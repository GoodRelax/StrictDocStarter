[DOCUMENT]
TITLE: Basics - review findings
UID: DOC-REVIEW
VERSION: 1.0

[GRAMMAR]
IMPORT_FROM_FILE: basic.sgra

[TEXT]
STATEMENT: >>>
**This document is the very reason `basic.sgra` exists.**

A review finding is not a standard StrictDoc concept either. If you force one
into the built-in `[REQUIREMENT]`, you have nowhere to put the severity or the
resolution status. So we added the `FINDING` node type to `basic.sgra` and
declared `SEVERITY` and `RESOLUTION` as fields of its own.

**Fix the choices in the grammar.** Write `SingleChoice(Major, Minor, Question)`
and StrictDoc turns a misspelling into a parse error on the spot and shows a
dropdown of the choices in the browser editor. Do not let the field take
arbitrary text.

Link a finding to the requirement it reviews with `ROLE: Reviews`. StrictDoc
then lists the finding on the requirement's screen as well, and one query pulls
it out of the JSON.
<<<

[FINDING]
UID: RV-001
TITLE: SW-002 does not say how to check the format
SEVERITY: Major
RESOLUTION: Open
STATEMENT: >>>
SW-002 does not say how the tool decides whether the format matches. Looking at
the extension and looking at the content lead to a different implementation and
to different steps in TC-002. Choose one of them.
<<<
RELATIONS:
- TYPE: Parent
  VALUE: SW-002
  ROLE: Reviews

[FINDING]
UID: RV-002
TITLE: SYS-003 offers no way to allow overwriting
SEVERITY: Question
RESOLUTION: Open
STATEMENT: >>>
Taking the safe side by default is reasonable, but the requirement leaves a user
who wants to overwrite on purpose no way out. We have not yet decided whether to
add an explicit option.
<<<
RELATIONS:
- TYPE: Parent
  VALUE: SYS-003
  ROLE: Reviews
