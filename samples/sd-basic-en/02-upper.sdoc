[DOCUMENT]
TITLE: Basics - system requirements
UID: DOC-UPPER
VERSION: 1.0

[GRAMMAR]
IMPORT_FROM_FILE: basic.sgra

[TEXT]
STATEMENT: >>>
This document states **what to build** and nothing else. It leaves how to build
it to `03-lower.sdoc`.

This paragraph is a `[TEXT]` node, and it carries no UID. **Do not give free
text a UID.** One test decides the matter - **give a node a UID when you want to
look it up by name later.** Nobody looks up an explanation or an introduction,
so leave those without one.
<<<

[REQUIREMENT]
UID: SYS-001
STATUS: Approved
TITLE: Converting a file
STATEMENT: >>>
The tool shall convert the input file that the user specifies into the output
format that the user specifies.
<<<
RATIONALE: >>>
This requirement is the reason the tool exists. If you drop it, every other
requirement loses its meaning.
<<<

[REQUIREMENT]
UID: SYS-002
STATUS: Approved
TITLE: Rejecting unexpected input
STATEMENT: >>>
When the input file is not in the format that the user specified, the tool shall
not convert it.
<<<

[REQUIREMENT]
UID: SYS-003
STATUS: Reviewed
TITLE: Protecting an existing file
STATEMENT: >>>
When a file with the same name already exists at the output destination, the
tool shall not overwrite it.
<<<
RATIONALE: >>>
If the tool destroys an existing file without a warning, the user never notices
that an irreversible operation happened. The tool takes the safe side by
default.
<<<
