[DOCUMENT]
TITLE: Basics - software requirements
UID: DOC-LOWER
VERSION: 1.0

[GRAMMAR]
IMPORT_FROM_FILE: basic.sgra

[TEXT]
STATEMENT: >>>
This document states **how to satisfy** each requirement in `02-upper.sdoc`.

**Write the parent-child link on the lower side.** Put `RELATIONS: TYPE: Parent`
on the software requirement and point it at the UID of the parent. Write nothing
on the system requirement. **Never list children on the upper side** - every new
software requirement would force you to touch the upper document, and you would
maintain the same link twice.

The parent **may live in another file.** StrictDoc collects every UID in the
project into a single table and then resolves the relations, so a file boundary
does not matter.
<<<

[REQUIREMENT]
UID: SW-001
STATUS: Approved
TITLE: Running the conversion
STATEMENT: >>>
The tool shall read the input file, convert it into the output format that the
user specified, and write the result to the output file.
<<<
RELATIONS:
- TYPE: Parent
  VALUE: SYS-001

[REQUIREMENT]
UID: SW-002
STATUS: Approved
TITLE: Checking the input format
STATEMENT: >>>
The tool shall check the format of the input file before it starts the
conversion. When the format differs from the one that the user specified, the
tool shall skip the conversion and exit with an error.
<<<
RELATIONS:
- TYPE: Parent
  VALUE: SYS-002

[REQUIREMENT]
UID: SW-003
STATUS: Approved
TITLE: Checking the destination
STATEMENT: >>>
The tool shall check whether a file with the same name exists before it writes
the output file. When such a file exists, the tool shall skip the write and exit
with an error.
<<<
RELATIONS:
- TYPE: Parent
  VALUE: SYS-003

[REQUIREMENT]
UID: SW-004
STATUS: Draft
TITLE: Atomic writing
STATEMENT: >>>
When something interrupts the write, the tool shall leave no incomplete file at
the output destination.
<<<
RATIONALE: >>>
If an incomplete file from an interrupted run survives, SW-003 treats it as an
existing file on the next run and stops. The user then sees an error exit with
no visible cause.
<<<
RELATIONS:
- TYPE: Parent
  VALUE: SYS-003
