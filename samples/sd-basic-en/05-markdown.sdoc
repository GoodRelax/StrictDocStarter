[DOCUMENT]
TITLE: Writing the body in Markdown
UID: DOC-MARKUP-MD
VERSION: 1.0
OPTIONS:
  MARKUP: Markdown

[GRAMMAR]
IMPORT_FROM_FILE: basic.sgra

[TEXT]
STATEMENT: >>>
**StrictDoc reads the body of this document, and only this document, as
Markdown.** The document declares that at the top.

```text
[DOCUMENT]
TITLE: ...
OPTIONS:
  MARKUP: Markdown
```

You can declare it in **only one place: `OPTIONS:` under `[DOCUMENT]`**. The
grammar allows no other spot. You cannot switch it per section or per
requirement.

The declaration covers **every multi-line field in that document**. It reaches
`STATEMENT`, it reaches `RATIONALE`, and it reaches a field you added in the
grammar such as `GIVEN`. It does not touch a single-line field such as
`UID:`.

**The browser gives you no way to set this.** The document-settings editor
offers only TITLE / UID / VERSION / CLASSIFICATION / PREFIX. You have no way to
add `OPTIONS:` other than typing it in a text editor.

**Traceability and JSON do not change at all.** Only the way StrictDoc draws the
body changes.
<<<

[[SECTION]]
TITLE: What you give up

[TEXT]
STATEMENT: >>>
**Every RST directive stops working.** StrictDoc shows an embedded image, a
formula, or a literal block as plain characters. Rewrite an image in the
Markdown notation `![alt](path)`.

**You also lose `[DOCUMENT_FROM_FILE]`.** That is why **this document cannot
pull in a figure.** Do not declare Markdown in a document that carries a figure.

**This is why `00-guide-for-human.sdoc` stays out of Markdown.** That document
uses both an image and an include.
<<<

[[/SECTION]]

[[SECTION]]
TITLE: What you gain

[TEXT]
STATEMENT: >>>
**You can use a pipe table, and it passes even when the columns do not line
up.** That is the biggest benefit.

| Table format | When the columns drift | Declaration |
| --- | --- | --- |
| grid | The export stops | Not needed |
| simple | It survives | Not needed |
| pipe | It survives | **MARKUP: Markdown required** |

The table above does not line up its column widths, and it still passes.
Compare it with the grid table in `00-guide-for-human.sdoc`. **In a document
where you keep adding tables by hand, that difference turns straight into a
difference in effort.**

A Mermaid code fence also becomes a figure as it stands. If you want to draw a
figure, though, move it out of this document into a fragment such as
`_assets/fig-flow.sdoc`. A fragment lets the main document stay in RST.
<<<

[[/SECTION]]

[[SECTION]]
TITLE: You write a requirement the same way

[TEXT]
STATEMENT: >>>
Only the way you write the body changes, so you write a requirement node exactly
as you write it in the other documents. The single requirement below links to
`SYS-001` in `01-upper.sdoc`. **This requirement exists only in the `.sdoc`
set** - `MARKUP: Markdown` is something only `.sdoc` can declare, so this
document has no counterpart in the `.md` set.
<<<

[REQUIREMENT]
UID: SW-005
STATUS: Draft
TITLE: Showing a conversion summary
REVIEW_STATUS: NotReviewed
STATEMENT: >>>
WHEN the conversion finishes, the tool shall print the following three items to
standard output on a single line.

- The name of the input file
- The name of the output file
- The time the conversion took

The tool shall use the format `<input> -> <output> (<seconds>s)`.
<<<
RATIONALE: >>>
When the user converts several files in a row, this line lets the user tell
which files finished and which ones remain.
<<<
RELATIONS:
- TYPE: Parent
  VALUE: SYS-001

[[/SECTION]]
