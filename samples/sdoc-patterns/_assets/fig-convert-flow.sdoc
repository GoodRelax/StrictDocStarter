[DOCUMENT]
TITLE: 図 - 変換処理の状態遷移
UID: FIG-CONVERT-FLOW
OPTIONS:
  MARKUP: Markdown

[TEXT]
STATEMENT: >>>
`01-requirements.sdoc` の PAT-001 / PAT-002 / PAT-003 が定める振る舞いを、
状態機械として 1 枚にしたもの。 **図の正本はこのファイルである。**

```mermaid
stateDiagram-v2
    [*] --> idle : start
    idle --> checking : input given
    checking --> converting : format ok
    checking --> stopped : unexpected format
    converting --> writing : converted
    writing --> done : written
    writing --> stopped : output exists
    done --> [*]
    stopped --> [*]
```

- `checking` で形式が違えば変換に入らず終わる (PAT-002)
- `writing` で出力先に既存ファイルがあれば上書きせず終わる (PAT-003)
- どちらの停止も異常終了ではなく、 仕様どおりの終了である

この文書は `OPTIONS: MARKUP: Markdown` を宣言しているので本文は Markdown であり、
` ```mermaid ` のフェンスがそのまま図になる。 拡張子が `.sdoc` なのは
`[DOCUMENT_FROM_FILE]` が `.sdoc` しか受け付けないためで、 書き方は Markdown のまま。
<<<
