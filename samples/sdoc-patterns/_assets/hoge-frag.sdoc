[DOCUMENT]
TITLE: まーくだんを (埋め込み用)
UID: HOGE-FRAG
OPTIONS:
  MARKUP: Markdown

[TEXT]
STATEMENT: >>>
# 埋め込まれる側

**この文書は `よみこむほう.sdoc` に取り込まれて、あちらの画面に直接出る。**
同時に、左の文書一覧からこのページ単体としても開ける。

本文は Markdown である (`OPTIONS: MARKUP: Markdown`)。だから表もフェンスもそのまま書ける。

| 今日の気分 | 明日の気分 |
| ---------- | ---------- |
| 良い       | 良い       |
| 悪い       | 良い       |

```mermaid
flowchart LR
    MD["_assets/hoge-frag.sdoc"] -->|"DOCUMENT_FROM_FILE"| PARENT["よみこむほう.sdoc"]
    MD -->|"個別ページとしても公開"| ALONE["hoge-frag.html"]
```

拡張子が `.sdoc` なのは `[DOCUMENT_FROM_FILE]` が `.sdoc` しか受け付けないためで、
書き方は Markdown のままである。`.md` を渡すと次で停止する。

    [DOCUMENT_FROM_FILE]: A document file name must have ".sdoc" extension
<<<
