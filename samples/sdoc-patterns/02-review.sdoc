[DOCUMENT]
TITLE: 書き方の型 - レビュー記録
UID: DOC-PATTERNS-REVIEW
VERSION: 1.0

[GRAMMAR]
IMPORT_FROM_FILE: patterns.sgra

[TEXT]
STATEMENT: >>>
「指摘」と「修正」は StrictDoc の標準概念ではない。 どちらもカスタム文法で作る。

- **指摘** — 独立したノード型 `[FINDING]` にし、 `ROLE: Reviews` で対象要求へ結ぶ。
- **修正** — 要求自身のフィールド `REVISION` にする。 対象と同じ場所にあるほうが追える。

こうしておくと、 どちらも JSON から 1 クエリで取り出せる。
引き方は `docs/03-sdoc-json-queries.md` の Q6 / Q7 にある。
<<<

[FINDING]
UID: FND-001
TITLE: PAT-003 が上書き可否を決めていなかった
SEVERITY: Major
RESOLUTION: Fixed
STATEMENT: >>>
初版の PAT-003 は「上書きしてもよい」と書いていたが、 利用者が
取り返しのつかない操作を無警告で起こせる。 既定は安全側に倒すべきである。
<<<
RELATIONS:
- TYPE: Parent
  VALUE: PAT-003
  ROLE: Reviews

[FINDING]
UID: FND-002
TITLE: PAT-002 の検査対象が書かれていない
SEVERITY: Question
RESOLUTION: Open
STATEMENT: >>>
「想定した形式か」の判定基準が書かれていない。 拡張子で見るのか、
中身を見るのかで実装が変わる。
<<<
RELATIONS:
- TYPE: Parent
  VALUE: PAT-002
  ROLE: Reviews
