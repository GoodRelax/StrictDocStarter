[DOCUMENT]
TITLE: 書き方の型 - 出力と問い合わせ
UID: DOC-PATTERNS-OUT
VERSION: 1.0

[GRAMMAR]
IMPORT_FROM_FILE: patterns.sgra

[TEXT]
STATEMENT: >>>
書いた `.sdoc` から何を取り出せるかをまとめる。 **HTML は人が読むため、
JSON は機械が引くため、 Markdown は他所へ渡すためのものである。**

::

    strictdoc export --formats=html     --output-dir out .
    strictdoc export --formats=json     --output-dir out .
    strictdoc export --formats=markdown --output-dir out .

`--formats` は他にも受け付ける。 一覧は ``strictdoc export --help`` で見る。
<<<

[[SECTION]]
TITLE: 1. JSON — 答えだけを取り出す

[TEXT]
STATEMENT: >>>
`out/json/index.json` が生まれる。 **要求を直したら毎回出し直す。**

問い合わせは `jq` で行う。 本サンプルの `queries/` に 7 本入れてある。

::

    jq -r -f queries/q6-findings.jq out/json/index.json

**フィルタを文字列で渡さずファイルに書くのは PowerShell のためである。**
PowerShell はクォートの中の `"` を落とすので `jq '...' file` の形が壊れる。
`-f` ならどの shell でも同じに動く。

各クエリの意味と実出力は `docs/03-sdoc-json-queries.md` にある。
<<<

[REQUIREMENT]
UID: PAT-010
STATUS: Approved
TITLE: JSON の大きさを見誤らない
STATEMENT: >>>
JSON を使う理由を「軽いから」と説明してはならない。 理由は
「全文を読まずに答えだけを引けるから」であること。
<<<
RATIONALE: >>>
`strictdoc` の JSON は元の `.sdoc` より**大きい**。 `json_generator.py` が
`json.dumps(..., indent=4)` を既定のまま呼ぶため、 4 スペースで整形され、
かつ**非 ASCII が ``\uXXXX`` に展開される** (日本語 1 文字が 3 バイトから
6 バイトになる)。 `sd-basic-ja` の実測で `.sdoc` の **3.49 倍**
(トークン数。 バイトでは 3.00 倍) であった。

`jq` を一度通せば元の文字に戻り、 整形も外れる。

::

    jq -c . out/json/index.json > out/json/index.min.json

同じ実測で **2.79 倍から 1.21 倍**まで下がった (バイトでは 3.23 → 1.27 倍)。
**一方、 クエリ 1 本の出力は `.sdoc` 全文の 0.02〜0.37 パーセントである。**
桁が違う。 **JSON を使う値打ちは小ささではなく、 引けることの側にある。**

トークン数は tiktoken の ``o200k_base`` による。 **これは OpenAI の
トークナイザであり他のモデルのものではない。** 同じ内容の別表現どうしを
比べる相対値としてのみ意味を持つ。
<<<

[[/SECTION]]

[[SECTION]]
TITLE: 2. Markdown — 渡す

[TEXT]
STATEMENT: >>>
`--formats=markdown` は `.sdoc` を `.md` に変換する。 StrictDoc を持たない
相手に渡すときに使う。

**カスタム文法を使ったまま往復させてはならない。** 出した `.md` を
StrictDoc が読み戻す際、 フィールドの順序が決まっており、 文法がその順に
宣言されていないと `Wrong field order` で落ちる。 順序は
`docs/02-sdoc-authoring.md` にある。

`.md` を**書く**側の形は `04-markdown-form.md` を参照。
<<<

[[/SECTION]]

[[SECTION]]
TITLE: 3. HTML — 読む

[TEXT]
STATEMENT: >>>
`launch-strictdoc.bat` にフォルダをドラッグすれば、 export せずにサーバが
立ち上がる。 編集して保存すれば再読み込みで反映される。

版と版の差分を見るには `project_features` に **`DIFF`** (experimental) を
足したうえで、 ``--generate-diff-dirs <old> <new>`` または
``--generate-diff-git "HEAD^..HEAD"`` を付ける。 **`DIFF` を足さないと
オプションを付けても差分ページは作られない。**
<<<

[[/SECTION]]
