[DOCUMENT]
TITLE: 書き方の型 - 図
UID: DOC-PATTERNS-FIG
VERSION: 1.0

[TEXT]
STATEMENT: >>>
図をこの文書へ集めたのは、 要求本体を人が読みやすく保つためである。
**JSON を軽くするためではない。** `md-sovd-automotive-ja` で実測したところ、
Mermaid が占めるのは JSON 全体の 1.4 パーセントであった
(`docs/02-sdoc-authoring.md` 参照)。

**図は要求文書に直接書かない。 1 枚 1 ファイルで `_assets/` に置き、 取り込む。**
本サンプルはこの 1 通りに統一してある。 実体は `_assets/fig-convert-flow.sdoc`。

::

    _assets/fig-convert-flow.sdoc
      [DOCUMENT]
      TITLE: 図 - 変換処理の状態遷移
      UID: FIG-CONVERT-FLOW
      OPTIONS:
        MARKUP: Markdown        <- 本文を Markdown として解釈させる

      [TEXT]
      STATEMENT: >>>
      ```mermaid  ...  ```      <- フェンスがそのまま図になる
      <<<

``OPTIONS: MARKUP: Markdown`` を宣言すると、 その文書の本文は Markdown になる。
だから mermaid のコードフェンスで書ける。
**RST の ``.. raw:: html`` に ``<pre class="mermaid">`` を埋める書き方は要らない。**

**拡張子は `.md` ではなく `.sdoc` にする。** 取り込みを行う `[DOCUMENT_FROM_FILE]` が
`.sdoc` 以外を拒否するためである (`processor.py` が拡張子を検査して停止する)。
中身の書き方は Markdown のままなので、 書き手が覚えることは増えない。

要求文書側は `[DOCUMENT_FROM_FILE]` で取り込む。 `01-requirements.sdoc` がこの形。

::

    [DOCUMENT_FROM_FILE]
    FILE: _assets/fig-convert-flow.sdoc

**これで図は要求の画面に直接表示され、 同時に 1 個の文書としても開ける。**
`strictdoc server` は取り込まれた文書も個別に公開するためである
(`launch-strictdoc.bat` はこの経路)。 `export` では既定で個別公開されないので、
必要なら `--included-documents` を付ける。

::

    strictdoc export --formats=html --included-documents --output-dir out .

**ただし JSON を引く目的でこのオプションを付けてはならない。** 取り込んだ文書が
独立文書としても重複し、 同じ UID が 2 か所に現れる。

**取り込みは 1 対 1 である。** 同じ図を 2 つの文書へ取り込むことはできない
(公式ユーザーガイド: "a document can be included to no more than one including
document")。 2 か所から参照したいなら、 一方は `[LINK: FIG-CONVERT-FLOW]` にする。

**プロジェクト内の `.md` は、 既定で全部 StrictDoc が文書として解析する。**
`_assets/` の中でも例外ではない。 **「アセット置き場だから解析されない」ということは
無い。** 文書の走査が無視するのは出力先フォルダだけで、 アセット置き場かどうかは
見ていない (`document_finder.py` はアセット探索と文書探索を別々に 2 回走らせる)。

**その実例が `_assets/note.md` である。** `#` の見出しで始まり、 その直下で
`**UID**:` を宣言してあるので、 本文からリンクの宛先にできる → [LINK: PATTERNS-NOTE]

**取り込みとの違いはリンク先に表でまとめてある。** 要点は 2 つで、
`[LINK:]` は `.md` も指せるが `[DOCUMENT_FROM_FILE]` は `.sdoc` しか受け付けないこと、
そして取り込みは 1 対 1 だがリンクは何個からでも指せることである。

そのため **文書として読めない `.md` が 1 つあると export 全体が止まる。**
最も多いのは見出しが無い場合で、 次のように言われる。

::

    Semantic error: Markdown parsing error: the document must start with an H1 heading.

つまり `.md` は **`#` の見出しで始めること。** どうしても文書にできないものは
`exclude_doc_paths` で名指しして外す。 本サンプルでは `queries/README.md` がそれ。

**除外はファイル単位で書くこと。 フォルダごと除外してはならない。**

::

    exclude_doc_paths=["_assets/notes.md"]   # OK。 その 1 ファイルだけ文書にしない
    exclude_doc_paths=["_assets/**"]         # 駄目。 画像も一緒に消える

`_assets/**` と書くとフォルダが走査から外れ、 **アセット置き場としても認識されなく
なるため画像がコピーされない。** それでも export は成功と報告し、 出来上がった
HTML の `<img>` だけが 404 になる。 気づきにくい。 **`exclude_doc_paths` は
文書探索とアセット探索の両方に渡されるためである。**

数式は `MATHJAX` で書ける。 `MERMAID` と同じく 0.27 以降は既定で有効なので、
`strictdoc_config.py` に列挙する必要は無い。 むしろ列挙すると DEPRECATION 警告が出る。

.. math::

    t_{\mathrm{total}} = t_{\mathrm{read}} + t_{\mathrm{convert}} + t_{\mathrm{write}}

画像は `_assets/` に置き、 `.. image::` で埋め込む。 このフォルダは StrictDoc が
自動でコピーするので、 **埋め込むだけなら設定ファイルに何も足さなくてよい。**

**SVG は拡大しても崩れないので、 図はこちらを既定にする。**

.. image:: _assets/pipeline.svg
   :alt: input file -> format check (PAT-002) -> convert (PAT-001) -> output file (PAT-003), with stop branches
   :width: 760px

**同じ図の PNG 版。** SVG を扱えない相手 (古いビューア、 一部の Office 貼り付け) 向けに
併置してある。 図の版が 2 つに増えるので、 **どちらが編集元かをファイル自身に書いておく。**

.. image:: _assets/pipeline.png
   :alt: the same flow as a raster image
   :width: 760px

`.md` から埋め込む形は `04-markdown-form.md` にある (`![alt](_assets/pipeline.png)`)。

<<<
