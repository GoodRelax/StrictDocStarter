[DOCUMENT]
TITLE: マークダウンを読み込むテスト

[TEXT]
STATEMENT: >>>
`_assets/` の中身を要求文書から使う方法を 3 つ並べてある。 **どれも実測で動く形である。**

1. `.md` へ**リンクを張る** — `[LINK: <UID>]`
2. `.md` の内容を**この画面に出す** — `[DOCUMENT_FROM_FILE]`
3. 画像を**埋め込む** — `.. image::`

**`.md` そのものを取り込むことはできない。** `[DOCUMENT_FROM_FILE]` は `.sdoc` しか
受け付けないため、 埋め込む側は `MARKUP: Markdown` を宣言した `.sdoc` にする。
書き方は Markdown のままでよい。
<<<

[REQUIREMENT]
UID: REQ-2
TITLE: .md へリンクを張る
STATEMENT: >>>
`_assets/hoge.md` は `#` の見出しで始まるので、 StrictDoc が 1 個の文書として
描画する。 その見出しの直下に UID を宣言してある。

::

    # まーくだんを

    **UID**: HOGE-DOC

これで `[LINK:]` の宛先になる。 本文からはこう書く → [LINK: HOGE-DOC]

**出力先のパスは書かない。** StrictDoc が UID から解決し、 リンク文字列は見出しの
文言から自動で付く。
<<<

[REQUIREMENT]
UID: REQ-3
TITLE: .md の内容をこの画面に出す
STATEMENT: >>>
リンクではなく**中身をここに出す**なら `[DOCUMENT_FROM_FILE]` で取り込む。
**この宣言は `STATEMENT` の中には書けない** — 文書の本体レベルに置く。
本書では末尾に置いてあり、 その位置に図と表が展開される。

::

    [DOCUMENT_FROM_FILE]
    FILE: _assets/hoge-frag.sdoc

取り込まれた側は `strictdoc server` では**個別ページとしても開ける**。
`export` のときだけ既定で個別公開されないので、 必要なら `--included-documents`
を付ける (ただし JSON を引く目的では付けてはならない。 同じ UID が 2 か所に出る)。
<<<

[REQUIREMENT]
UID: REQ-1
TITLE: 画像を埋め込む
STATEMENT: >>>
画像は `_assets/` に置いて `.. image::` で埋め込む。 このフォルダは StrictDoc が
自動でコピーするので、 設定に何も足さなくてよい。

.. image:: _assets/pipeline.svg
   :width: 600px

.. image:: _assets/pipeline.png
   :width: 600px
<<<

[DOCUMENT_FROM_FILE]
FILE: _assets/hoge-frag.sdoc
