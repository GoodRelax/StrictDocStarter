[DOCUMENT]
TITLE: 書き方の型 - まず最小のものを

[TEXT]
STATEMENT: >>>
**自分の要求書を書き始めるなら、 このファイルを写すところから始める。**
本サンプルで唯一、 カスタム文法を使っていない文書である。

必要なものは 3 つしかない。

- `[DOCUMENT]` — 先頭に 1 つ。 `TITLE:` だけあればよい。
- `[REQUIREMENT]` — 要求 1 件につき 1 つ。
- `RELATIONS:` — 要求どうしを結ぶとき。

`UID:` は付けなくても解析は通るが、 **付けないと他から参照できず JSON からも
引けない。** 最初から付けること。

以降の文書 (`01` 以降) は、 ここに文法・レビュー記録・図・出力の型を足していく。
足す前に、 まずこの形が動くことを確かめるとよい。
<<<

[REQUIREMENT]
UID: REQ-4
TITLE: あだｓだ
STATEMENT: >>>
あｓｄふぁ
<<<

[REQUIREMENT]
UID: HELLO-001
TITLE: メッセージの表示
STATEMENT: >>>
本システムは、 利用者に対して "Hello, World" のメッセージを画面に表示すること。
<<<

[REQUIREMENT]
UID: HELLO-002
TITLE: 日本語の表示
STATEMENT: >>>
表示するメッセージは、 UTF-8 で符号化された日本語文字列を含むことができること。
<<<
RELATIONS:
- TYPE: Parent
  VALUE: HELLO-001

[REQUIREMENT]
UID: HELLO-003
TITLE: 標準出力への出力
STATEMENT: >>>
本システムは、 標準出力デバイス (コンソール、 ターミナル等) にメッセージを
出力すること。
<<<
RELATIONS:
- TYPE: Parent
  VALUE: HELLO-001
