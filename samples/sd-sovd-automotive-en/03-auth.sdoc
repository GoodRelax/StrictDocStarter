[DOCUMENT]
TITLE: SOVD Authentication & Authorization Requirements
UID: DOC-SOVD-AUTH
VERSION: 1.0

[GRAMMAR]
IMPORT_FROM_FILE: sovd-grammar.sgra

[TEXT]
STATEMENT: >>>
This document defines the SOVD **authentication and authorization** requirements
from L1 (system) down to L3 (unit). For the stakeholder requirements (L0) and use
cases, see `01-stakeholder-requirements.sdoc`; for the shared front matter
(purpose, terminology, notation, the ASIL/CAL split, referenced standards), see
`00-overview.sdoc`.

Domain-specific referenced standards: OAuth 2.0 (RFC 6749) / PKCE (RFC 7636) /
JWT (RFC 7519) / TLS 1.3 (RFC 8446) / ISO/SAE 21434 (CAL). Because authentication
and authorization are **cybersecurity** functions, the requirements in this
document are, as a rule, **ASIL=QM**, with the assurance level expressed via
**CAL** (see 00-overview Section 6.3).
<<<

[[SECTION]]
TITLE: L1 - System Requirements

[TEXT]
STATEMENT: >>>
**L1 representative sequence: authenticated data read**

The typical SOVD flow proceeds in the order: (1) OAuth2 PKCE authentication ->
(2) access token (JWT) issuance -> (3) resource request with a Bearer token ->
(4) scope verification -> (5) translation to UDS and response. Vehicle data must
not be returned before scope verification (AUTH-L1-011).

.. raw:: html

    <pre class="mermaid">
    sequenceDiagram
        participant C as SOVD Client
        participant G as Gateway ECU
        participant E as Engine ECU
        C->>G: POST /auth/token (OAuth2 PKCE)
        G-->>C: 200 access_token (JWT)
        C->>G: GET /components/engine/data/rpm (Bearer JWT)
        G->>G: verify JWT + scope read:did
        G->>E: ReadDataByIdentifier (DID 0xF40C)
        E-->>G: rpm = 824
        G-->>C: 200 OK (rpm=824)
    </pre>
<<<

[REQUIREMENT]
UID: AUTH-L1-001
TITLE: OAuth 2.0 PKCE authentication flow
TYPE: Functional
ASIL: QM
CAL: CAL3
LAYER: L1_System
STATEMENT: >>>
When a client requests authentication, the vehicle shall perform client
authentication using the OAuth 2.0 Authorization Code Flow with PKCE.
<<<
VERIFICATION: >>>
An access token can be obtained via the authorization code flow with PKCE, and
authentication is rejected when the code_verifier does not match.
<<<
RELATIONS:
- TYPE: Parent
  VALUE: AUTH-L0-001

[REQUIREMENT]
UID: AUTH-L1-002
TITLE: Access token issuance
TYPE: Functional
ASIL: QM
CAL: CAL3
LAYER: L1_System
STATEMENT: >>>
When authentication succeeds, the vehicle shall issue an access token in JWT
(RFC 7519) format.
<<<
VERIFICATION: >>>
The successful-authentication response contains an access_token in JWT format.
<<<
RELATIONS:
- TYPE: Parent
  VALUE: AUTH-L1-001

[REQUIREMENT]
UID: AUTH-L1-003
TITLE: Access token contents
TYPE: Non-Functional
ASIL: QM
CAL: CAL2
LAYER: L1_System
STATEMENT: >>>
The access token issued by the vehicle shall include the expiry (exp), the scope
(scope), and the subject ID (sub).
<<<
RATIONALE: >>>
Guarantees the minimum claims required for revocation and authorization decisions.
<<<
RELATIONS:
- TYPE: Parent
  VALUE: AUTH-L1-002

[REQUIREMENT]
UID: AUTH-L1-004
TITLE: Role-based access control (RBAC)
TYPE: Functional
ASIL: QM
CAL: CAL3
LAYER: L1_System
STATEMENT: >>>
The vehicle shall allow scopes (read:did / read:dtc / write:dtc / write:swupdate,
etc.) to be assigned per role (Mechanic / OEMEngineer / FleetOperator).
<<<
RELATIONS:
- TYPE: Parent
  VALUE: AUTH-L0-002

[REQUIREMENT]
UID: AUTH-L1-005
TITLE: TLS 1.3 encryption of the communication channel
TYPE: Non-Functional
ASIL: QM
CAL: CAL3
LAYER: L1_System
STATEMENT: >>>
The vehicle shall encrypt all communication between the SOVD client and the
gateway with TLS 1.3 or higher.
<<<
VERIFICATION: >>>
The handshake is established with TLS 1.3 or higher, and plaintext HTTP
connections are rejected.
<<<
RELATIONS:
- TYPE: Parent
  VALUE: AUTH-L0-003

[REQUIREMENT]
UID: AUTH-L1-006
TITLE: Prohibition of TLS downgrade
TYPE: Restriction
ASIL: QM
CAL: CAL3
LAYER: L1_System
STATEMENT: >>>
If a client requests a downgrade to TLS 1.2 or lower, then the vehicle shall
reject the connection.
<<<
RATIONALE: >>>
Prevents the weakening of cryptographic strength caused by downgrade attacks.
<<<
RELATIONS:
- TYPE: Parent
  VALUE: AUTH-L1-005

[REQUIREMENT]
UID: AUTH-L1-007
TITLE: Mutual TLS (mTLS) authentication
TYPE: Functional
ASIL: QM
CAL: CAL3
LAYER: L1_System
STATEMENT: >>>
In configurations that use an OEM-internal connection, the vehicle shall
additionally support mutual TLS authentication using a client certificate (X.509).
<<<
RELATIONS:
- TYPE: Parent
  VALUE: AUTH-L0-003

[REQUIREMENT]
UID: AUTH-L1-008
TITLE: Access token expiry
TYPE: Non-Functional
ASIL: QM
CAL: CAL2
LAYER: L1_System
STATEMENT: >>>
The expiry of the access token issued by the vehicle shall default to 30 minutes
and shall not exceed 60 minutes.
<<<
VERIFICATION: >>>
The exp of a default-issued token is 30 minutes from issuance, and even at the
configurable upper bound it does not exceed 60 minutes.
<<<
RELATIONS:
- TYPE: Parent
  VALUE: AUTH-L1-002

[REQUIREMENT]
UID: AUTH-L1-009
TITLE: Token revocation API
TYPE: Functional
ASIL: QM
CAL: CAL3
LAYER: L1_System
STATEMENT: >>>
The vehicle shall provide an API to revoke an already-issued access token.
<<<
RELATIONS:
- TYPE: Parent
  VALUE: AUTH-L0-001

[REQUIREMENT]
UID: AUTH-L1-010
TITLE: Rejection of revoked tokens
TYPE: Restriction
ASIL: QM
CAL: CAL3
LAYER: L1_System
STATEMENT: >>>
If access is attempted with a revoked access token, then the vehicle shall
immediately reject that request.
<<<
VERIFICATION: >>>
After the revocation API is executed, access with the same token results in
HTTP 401.
<<<
RELATIONS:
- TYPE: Parent
  VALUE: AUTH-L1-009

[REQUIREMENT]
UID: AUTH-L1-011
TITLE: Prohibition of returning data before scope verification
TYPE: Restriction
ASIL: QM
CAL: CAL3
LAYER: L1_System
STATEMENT: >>>
The vehicle shall not return vehicle data before verification of the requested
scope succeeds.
<<<
RATIONALE: >>>
Structurally prevents data leakage prior to authentication and authorization by
guaranteeing message ordering.
<<<
VERIFICATION: >>>
A request with insufficient scope returns HTTP 403 without including any vehicle
data.
<<<
RELATIONS:
- TYPE: Parent
  VALUE: AUTH-L0-004
- TYPE: Parent
  VALUE: AUTH-L0-002

[REQUIREMENT]
UID: AUTH-L1-012
TITLE: Audit log recording
TYPE: Functional
ASIL: QM
CAL: CAL2
LAYER: L1_System
STATEMENT: >>>
The vehicle shall be able to record authentication and authorization events
(token issuance, verification, revocation, access-decision outcomes) as an audit log.
<<<
RELATIONS:
- TYPE: Parent
  VALUE: AUTH-L0-006

[[/SECTION]]

[[SECTION]]
TITLE: L2 - ECU Software Requirements

[TEXT]
STATEMENT: >>>
**L2 formulas: signature verification and latency budget**

For RSA signature verification of the JWT, the hash recovered by the following
formula from the signature :math:`s`, the public exponent :math:`e`, and the
modulus :math:`n` is compared with the hash of the received message:

.. math::

    m \equiv s^{e} \pmod{n}

The latency budget for authentication processing (token verification + scope
decision) satisfies the following (AUTH-L2-006):

.. math::

    t_{\mathrm{auth}} = t_{\mathrm{verify}} + t_{\mathrm{scope}} \le 50\,\mathrm{ms}
<<<

[REQUIREMENT]
UID: AUTH-L2-001
TITLE: Authentication endpoint
TYPE: Functional
ASIL: QM
CAL: CAL3
LAYER: L2_ECU_SW
STATEMENT: >>>
When a client sends an OAuth 2.0 Token Request, the gateway ECU shall accept it
at the HTTPS POST /auth/token endpoint.
<<<
RELATIONS:
- TYPE: Parent
  VALUE: AUTH-L1-001

[REQUIREMENT]
UID: AUTH-L2-002
TITLE: JWT verification
TYPE: Functional
ASIL: QM
CAL: CAL3
LAYER: L2_ECU_SW
STATEMENT: >>>
When an access token is received, the gateway ECU shall verify the signature,
expiry, and scope using RFC 7519-compliant verification.
<<<
RELATIONS:
- TYPE: Parent
  VALUE: AUTH-L1-002

[REQUIREMENT]
UID: AUTH-L2-003
TITLE: Scope checkpoint
TYPE: Functional
ASIL: QM
CAL: CAL3
LAYER: L2_ECU_SW
STATEMENT: >>>
If a request does not include the required scope, then the gateway ECU shall
return HTTP 403 before the diagnostic API handler processes it.
<<<
VERIFICATION: >>>
A request lacking the required scope results in 403 without reaching the target ECU.
<<<
RELATIONS:
- TYPE: Parent
  VALUE: AUTH-L1-004
- TYPE: Parent
  VALUE: AUTH-L1-011

[REQUIREMENT]
UID: AUTH-L2-004
TITLE: TLS termination and attachment of authentication context
TYPE: Functional
ASIL: QM
CAL: CAL3
LAYER: L2_ECU_SW
STATEMENT: >>>
The gateway ECU shall terminate TLS 1.3 at the external interface. WHEN the
gateway ECU forwards a message to the internal in-vehicle network, it shall
attach the authentication context to that message.
<<<
RELATIONS:
- TYPE: Parent
  VALUE: AUTH-L1-005

[REQUIREMENT]
UID: AUTH-L2-005
TITLE: Integrity verification of the client certificate store
TYPE: Functional
ASIL: QM
CAL: CAL3
LAYER: L2_ECU_SW
STATEMENT: >>>
When it starts up, the gateway ECU shall verify the integrity of the
non-volatile area that stores the certificate chain of the trusted client CA.
<<<
RELATIONS:
- TYPE: Parent
  VALUE: AUTH-L1-007

[REQUIREMENT]
UID: AUTH-L2-006
TITLE: Authentication processing latency
TYPE: Non-Functional
ASIL: QM
CAL: CAL2
LAYER: L2_ECU_SW
STATEMENT: >>>
The combined latency of token verification and scope checking on the gateway ECU
shall be within 50 ms (satisfying t_auth in the formula above).
<<<
VERIFICATION: >>>
Under representative load, the 95th percentile of token verification + scope
decision is within 50 ms.
<<<
RELATIONS:
- TYPE: Parent
  VALUE: AUTH-L2-002

[REQUIREMENT]
UID: AUTH-L2-007
TITLE: Revocation list synchronization
TYPE: Functional
ASIL: QM
CAL: CAL3
LAYER: L2_ECU_SW
STATEMENT: >>>
At vehicle startup and every hour thereafter, the gateway ECU shall fetch the
revoked-token list from the OEM authentication server and update its local cache.
<<<
RELATIONS:
- TYPE: Parent
  VALUE: AUTH-L1-009

[REQUIREMENT]
UID: AUTH-L2-008
TITLE: Retention of authentication logs
TYPE: Constraint
ASIL: QM
CAL: CAL2
LAYER: L2_ECU_SW
STATEMENT: >>>
The gateway ECU shall retain all authentication attempts (success and failure) in
the non-volatile area for at least 30 days.
<<<
RATIONALE: >>>
Required for tracing unauthorized access (forensics).
<<<
RELATIONS:
- TYPE: Parent
  VALUE: AUTH-L1-012

[[/SECTION]]

[[SECTION]]
TITLE: L3 - Unit / Software Component Requirements

[REQUIREMENT]
UID: AUTH-L3-001
TITLE: TokenVerifier unit
TYPE: Functional
ASIL: QM
CAL: CAL3
LAYER: L3_Unit
STATEMENT: >>>
The TokenVerifier unit shall be implemented as a pure function that takes a JWT
string as input and returns the results of signature verification, expiry
checking, and claim parsing.
<<<
VERIFICATION: >>>
For test vectors of known valid/invalid tokens, it returns the expected outcome
and reason code.
<<<
RELATIONS:
- TYPE: Parent
  VALUE: AUTH-L2-002

[REQUIREMENT]
UID: AUTH-L3-002
TITLE: TokenCache unit capacity
TYPE: Non-Functional
ASIL: QM
CAL: CAL2
LAYER: L3_Unit
STATEMENT: >>>
The TokenCache unit shall hold up to 1,024 verified tokens using LRU and keep
memory usage within 256 KB.
<<<
RATIONALE: >>>
Curbs authentication latency (AUTH-L2-006) by reusing verified tokens.
<<<
RELATIONS:
- TYPE: Parent
  VALUE: AUTH-L2-006

[REQUIREMENT]
UID: AUTH-L3-003
TITLE: Restriction on implementation language and dependencies
TYPE: Constraint
ASIL: QM
CAL: CAL2
LAYER: L3_Unit
STATEMENT: >>>
The authentication-related units shall be implemented in MISRA C:2012-compliant C,
with external dependencies limited to OpenSSL / cJSON only.
<<<

[[/SECTION]]
