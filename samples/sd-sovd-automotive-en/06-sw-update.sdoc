[DOCUMENT]
TITLE: SOVD Software Update (OTA) Requirements (Software Update)
UID: DOC-SOVD-UPDATE
VERSION: 1.0

[GRAMMAR]
IMPORT_FROM_FILE: sovd-grammar.sgra

[TEXT]
STATEMENT: >>>
This document defines the requirements for **OTA (Over-The-Air) software update** via SOVD,
from L1 (system) down to L3 (unit). It covers the four phases of download, signature
verification, installation, and rollback, as well as update-time protection for functional
safety (ISO 26262) related ECUs. Stakeholder requirements (L0) and use cases are assumed
from `01-stakeholder-requirements.sdoc`, the shared front matter from
`00-overview.sdoc`, and authentication and authorization from `03-auth.sdoc`.

This document is a domain where **safety (ASIL) and security (CAL) intersect**. The ban on
flash writing while the vehicle is moving is **safety (ASIL D)**, and signature verification
**prevents the installation of tampered firmware**, having both safety and security aspects,
so it is assigned **ASIL D and CAL4** (00-overview §6.3).
<<<

[[SECTION]]
TITLE: L1 - System Requirements (System Requirements)

[TEXT]
STATEMENT: >>>
**L1 state machine: OTA update phases**

The OTA update follows the state machine below. If signature verification (Verifying) fails,
it does not transition to Installing but becomes Failed, and if writing (Installing) fails,
it returns to the previous version via RolledBack. This structurally prohibits "installation
of an unverified package" (SWU-L1-008).

.. raw:: html

    <pre class="mermaid">
    stateDiagram-v2
        [*] --> Idle
        Idle --> Downloading: POST /updates
        Downloading --> Verifying: package received
        Verifying --> Installing: signature valid
        Verifying --> Failed: signature invalid
        Installing --> Activated: flash OK
        Installing --> RolledBack: flash error
        Activated --> [*]
        RolledBack --> Idle
        Failed --> Idle
    </pre>
<<<

[REQUIREMENT]
UID: SWU-L1-001
TITLE: Update package download
TYPE: Functional
ASIL: QM
CAL: CAL3
LAYER: L1_System
STATEMENT: >>>
The vehicle shall provide the POST /updates endpoint and retrieve the update package
(binary + manifest + signature) from the OEM server.
<<<
RELATIONS:
- TYPE: Parent
  VALUE: SWU-L0-001
- TYPE: Parent
  VALUE: SWU-L0-007

[REQUIREMENT]
UID: SWU-L1-002
TITLE: Package signature verification
TYPE: Functional
ASIL: D
CAL: CAL4
LAYER: L1_System
STATEMENT: >>>
When a package has been downloaded, the vehicle shall verify an RSA-PSS signature of 2048-bit or stronger against the OEM root certificate chain.
<<<
VERIFICATION: >>>
Signature verification of a tampered package shall be determined as failed (invalid).
<<<
RELATIONS:
- TYPE: Parent
  VALUE: SWU-L0-002

[REQUIREMENT]
UID: SWU-L1-003
TITLE: A/B partition switchover
TYPE: Functional
ASIL: D
LAYER: L1_System
STATEMENT: >>>
The vehicle's ECU shall have an A/B partition configuration, write the new firmware to the
inactive partition, and switch over via the bootloader. If the switchover fails, it shall
retain the previous partition.
<<<
RELATIONS:
- TYPE: Parent
  VALUE: SWU-L0-003

[REQUIREMENT]
UID: SWU-L1-004
TITLE: Driving-state guard
TYPE: Functional
ASIL: D
LAYER: L1_System
STATEMENT: >>>
Before starting a flash write, the vehicle shall confirm that all of the following conditions
are met: (a) vehicle speed == 0, (b) parking brake ON, (c) shift in Park, (d) IG-OFF or ACC state.
<<<
VERIFICATION: >>>
With any one of the four conditions broken, a flash write shall not be started.
<<<
RELATIONS:
- TYPE: Parent
  VALUE: SWU-L0-004

[REQUIREMENT]
UID: SWU-L1-005
TITLE: Rollback API
TYPE: Functional
ASIL: C
LAYER: L1_System
STATEMENT: >>>
The vehicle shall be able to perform an immediate rollback to the previous version via
POST /updates/rollback. While a rollback is in progress, the system shall not accept new
update, flash-write, or diagnostic-write operation requests.
<<<
RELATIONS:
- TYPE: Parent
  VALUE: SWU-L0-003

[REQUIREMENT]
UID: SWU-L1-006
TITLE: Update progress stream
TYPE: Functional
ASIL: QM
LAYER: L1_System
STATEMENT: >>>
The vehicle shall push the update progress (0..100%) and current phase of each ECU to the
SOVD client via GET /updates/progress (Server-Sent Events).
<<<
RELATIONS:
- TYPE: Parent
  VALUE: SWU-L0-008

[REQUIREMENT]
UID: SWU-L1-007
TITLE: Interruption tolerance
TYPE: Functional
ASIL: QM
LAYER: L1_System
STATEMENT: >>>
If a power loss or communication disconnection occurs during an update, then on resumption
the vehicle shall resume if it was downloading, retry from the beginning if it was writing,
and skip if it was already complete.
<<<
RELATIONS:
- TYPE: Parent
  VALUE: SWU-L0-003

[REQUIREMENT]
UID: SWU-L1-008
TITLE: Compliance with the OTA state machine
TYPE: Functional
ASIL: D
CAL: CAL4
LAYER: L1_System
STATEMENT: >>>
The vehicle's OTA update shall follow the state machine shown above. If signature
verification (Verifying) fails, it shall not transition to Installing but become Failed, and
on a flash failure it shall return to the previous version via RolledBack.
<<<
RATIONALE: >>>
Installation of a package that failed signature verification is structurally prohibited through state transitions. Because the same state machine also handles the RolledBack transition on a flash failure, it is an example of convergence (N->1) that satisfies both tampering detection (SWU-L0-002) and automatic rollback on a write failure with a single state machine (anomaly detection and manual rollback are handled by SWU-L1-005).
<<<
RELATIONS:
- TYPE: Parent
  VALUE: SWU-L0-006
- TYPE: Parent
  VALUE: SWU-L0-003

[[/SECTION]]

[[SECTION]]
TITLE: L2 - ECU Software Requirements (ECU Software Requirements)

[REQUIREMENT]
UID: SWU-L2-001
TITLE: Download manager
TYPE: Functional
ASIL: QM
CAL: CAL3
LAYER: L2_ECU_SW
STATEMENT: >>>
The gateway ECU shall implement the DownloadManager and perform segmented downloading via
HTTPS Range requests, progress reporting, and integrity checking (SHA-256).
<<<
RELATIONS:
- TYPE: Parent
  VALUE: SWU-L1-001

[REQUIREMENT]
UID: SWU-L2-002
TITLE: Signature verification engine
TYPE: Functional
ASIL: D
CAL: CAL4
LAYER: L2_ECU_SW
STATEMENT: >>>
The SignatureVerifier shall support both ECDSA P-256 and RSA-PSS 2048, and verify the
signature chain against the OEM root CA.
<<<
RELATIONS:
- TYPE: Parent
  VALUE: SWU-L1-002

[REQUIREMENT]
UID: SWU-L2-003
TITLE: Flash write driver
TYPE: Functional
ASIL: D
LAYER: L2_ECU_SW
STATEMENT: >>>
The FlashWriter shall handle writing to the ECU's internal NOR flash and shall make a CRC32
verification mandatory after writing.
<<<
RELATIONS:
- TYPE: Parent
  VALUE: SWU-L1-003

[REQUIREMENT]
UID: SWU-L2-004
TITLE: VehicleStateGuard
TYPE: Functional
ASIL: D
LAYER: L2_ECU_SW
STATEMENT: >>>
From before the update starts, the VehicleStateGuard shall monitor the four conditions of
SWU-L1-004 at a 50 ms cycle. IF even one of them breaks, THEN the VehicleStateGuard shall
emergency-abort the write.
<<<
RELATIONS:
- TYPE: Parent
  VALUE: SWU-L1-004

[REQUIREMENT]
UID: SWU-L2-005
TITLE: Rollback manager
TYPE: Functional
ASIL: C
LAYER: L2_ECU_SW
STATEMENT: >>>
The RollbackManager shall retain the previous version's partition information and, on a
rollback request, rewrite the bootloader parameters and request a restart.
<<<
RELATIONS:
- TYPE: Parent
  VALUE: SWU-L1-005

[REQUIREMENT]
UID: SWU-L2-006
TITLE: Progress event bus
TYPE: Functional
ASIL: QM
LAYER: L2_ECU_SW
STATEMENT: >>>
Each update phase (download / verify / write / finalize) shall publish an event to the
ProgressEventBus, and the SSE endpoint shall subscribe and deliver it.
<<<
RELATIONS:
- TYPE: Parent
  VALUE: SWU-L1-006

[REQUIREMENT]
UID: SWU-L2-007
TITLE: Resumable state machine
TYPE: Functional
ASIL: QM
LAYER: L2_ECU_SW
STATEMENT: >>>
The state of the update state machine shall be saved in non-volatile memory and be able to
resume from the last safe state on a restart after a power loss.
<<<
RELATIONS:
- TYPE: Parent
  VALUE: SWU-L1-007

[REQUIREMENT]
UID: SWU-L2-008
TITLE: ASIL D development process
TYPE: Constraint
ASIL: D
LAYER: L2_ECU_SW
STATEMENT: >>>
The SignatureVerifier / FlashWriter / VehicleStateGuard shall be built with an ISO 26262
ASIL D compliant development process and achieve 100% unit test coverage.
<<<
RELATIONS:
- TYPE: Parent
  VALUE: SWU-L1-002

[[/SECTION]]

[[SECTION]]
TITLE: L3 - Unit Requirements (Unit / Software Component Requirements)

[REQUIREMENT]
UID: SWU-L3-001
TITLE: PackageDownloader unit
TYPE: Functional
ASIL: QM
CAL: CAL3
LAYER: L3_Unit
STATEMENT: >>>
The PackageDownloader unit shall implement HTTPS Range downloading in 1 MB chunks and provide
retry on failure (exponential backoff 1s..30s).
<<<
RELATIONS:
- TYPE: Parent
  VALUE: SWU-L2-001

[REQUIREMENT]
UID: SWU-L3-002
TITLE: SignatureVerifier unit
TYPE: Functional
ASIL: D
CAL: CAL4
LAYER: L3_Unit
STATEMENT: >>>
The SignatureVerifier unit shall be implemented as a stateless pure function that verifies
ECDSA P-256 and RSA-PSS 2048 signatures using OpenSSL.
<<<
RELATIONS:
- TYPE: Parent
  VALUE: SWU-L2-002

[REQUIREMENT]
UID: SWU-L3-003
TITLE: FlashSectorWriter unit
TYPE: Functional
ASIL: D
LAYER: L3_Unit
STATEMENT: >>>
The FlashSectorWriter unit shall provide erase, write and CRC32 computation for 64 KB
sectors. The write operation shall require a prior sector erasure. IF the erase or the write
fails, THEN the FlashSectorWriter unit shall return ERROR_FLASH_VERIFY.
<<<
RELATIONS:
- TYPE: Parent
  VALUE: SWU-L2-003

[REQUIREMENT]
UID: SWU-L3-004
TITLE: VehicleStateMonitor unit
TYPE: Functional
ASIL: D
LAYER: L3_Unit
STATEMENT: >>>
The VehicleStateMonitor unit shall read the vehicle speed, parking brake, shift and IG
signals from the CAN bus. IF all four conditions hold, THEN the VehicleStateMonitor unit shall
return TRUE. Otherwise it shall return FALSE.
<<<
RELATIONS:
- TYPE: Parent
  VALUE: SWU-L2-004

[REQUIREMENT]
UID: SWU-L3-005
TITLE: Development language restriction
TYPE: Constraint
ASIL: D
LAYER: L3_Unit
STATEMENT: >>>
ASIL D certified units shall be implemented only in MISRA C:2012 compliant C, with dynamic
memory allocation prohibited, recursive calls prohibited, and the cyclomatic complexity of
every function <= 10.
<<<
RELATIONS:
- TYPE: Parent
  VALUE: SWU-L2-008

[[/SECTION]]
