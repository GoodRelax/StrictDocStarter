[DOCUMENT]
TITLE: SOVD Architecture Specification (System Architecture)
UID: DOC-SOVD-ARCH
VERSION: 1.0

[GRAMMAR]
IMPORT_FROM_FILE: sovd-grammar.sgra

[TEXT]
STATEMENT: >>>
This document defines the **architecture (design / HOW)** of the SOVD vehicle diagnostics
system from a whole-system perspective. It captures the structure that realizes the
requirements (01, 03-07, WHAT) - the approach, components, modules, domain model, behavior,
and design decisions.

**Design granularity rule:** Each component expresses its **single responsibility (SRP) in one
sentence** and is given a name that denotes that responsibility. Interfaces/structure are shown
in the **class diagrams** (3.4), and each individual **behavior (the specification of a
responsibility)** is expressed by a **test (10) scenario** (1 behavior = 1 scenario = 1
verdict). Each component traces to the requirement it realizes via an ``Implements`` relation.

The shared front matter is in `00-overview.sdoc`, the API contract in `09-api.sdoc`, and the
tests in `10-test-spec.sdoc`.
<<<

[[SECTION]]
TITLE: 3.1 Architecture Concept (Architecture Concept)

[TEXT]
STATEMENT: >>>
**Approach:** Layered + separation of platform/feature. The vehicle gateway ECU terminates
SOVD (HTTP/TLS) and bridges internally to UDS (00-overview §3.1). The feature domains are built
on top of the common platform (07), and the dependency direction is one-way: feature ->
platform. Component diagrams and class diagrams are color-coded by Clean Architecture (CA)
layer. Legend:

.. raw:: html

    <pre class="mermaid">
    graph RL
        subgraph Legend["CA Layer Legend (dependency direction)"]
            direction RL
            F["Framework"]:::framework -->|depends on| A["Adapter"]:::adapter
            A -->|depends on| U["Use Case"]:::usecase
            U -->|depends on| E["Entity"]:::entity
        end
        classDef entity fill:#FF8C00,stroke:#333,color:#000
        classDef usecase fill:#FFD700,stroke:#333,color:#000
        classDef adapter fill:#90EE90,stroke:#333,color:#000
        classDef framework fill:#87CEEB,stroke:#333,color:#000
    </pre>

Entity=orange / Use Case=gold / Adapter=green / Framework=blue.
<<<

[[/SECTION]]

[[SECTION]]
TITLE: 3.2 Components (Components)

[TEXT]
STATEMENT: >>>
**Representative slice: authenticated DID read (color-coded by CA layer)**

**This figure runs past 15 lines, so it lives in its own document** -> [LINK: DOC-FIG-ARCH-CONTEXT]

Below, the main components of all domains are defined by their **single responsibility (one
sentence)** and traced to requirements. For individual behaviors (acceptance/unit verdicts),
refer to the scenarios in 10.
<<<

[TEXT]
STATEMENT: >>>
**Platform components (Common Platform)**
<<<

[COMPONENT]
UID: ARCH-C-001
TITLE: TlsTerminator
CA_LAYER: Framework
STATEMENT: >>>
Terminates TLS 1.3 for external communication.
<<<
MODULE: src/platform/tls_terminator.c
RELATIONS:
- TYPE: Parent
  VALUE: PLAT-L3-003
  ROLE: Implements

[COMPONENT]
UID: ARCH-C-002
TITLE: ScopeAuthorizer
CA_LAYER: UseCase
STATEMENT: >>>
Determines whether a diagnostic operation is authorized based on the requested scope.
<<<
MODULE: src/platform/scope_authorizer.c
RELATIONS:
- TYPE: Parent
  VALUE: PLAT-L3-002
  ROLE: Implements

[COMPONENT]
UID: ARCH-C-003
TITLE: UdsClient
CA_LAYER: Adapter
STATEMENT: >>>
Sends and receives UDS frames to and from the in-vehicle ECUs (with reliability control including timeouts, retries, and NRC).
<<<
MODULE: src/platform/uds_client.c
RELATIONS:
- TYPE: Parent
  VALUE: PLAT-L3-001
  ROLE: Implements

[COMPONENT]
UID: ARCH-C-004
TITLE: JsonSerializer
CA_LAYER: Adapter
STATEMENT: >>>
Converts diagnostic data into the ASAM SOVD JSON format.
<<<
MODULE: src/platform/json_serializer.c
RELATIONS:
- TYPE: Parent
  VALUE: PLAT-L3-004
  ROLE: Implements

[TEXT]
STATEMENT: >>>
**Authentication domain (03-auth)**
<<<

[COMPONENT]
UID: ARCH-C-005
TITLE: TokenVerifier
CA_LAYER: UseCase
STATEMENT: >>>
Verifies the validity (signature, expiry, claims) of an access token (JWT).
<<<
MODULE: src/auth/token_verifier.c
RELATIONS:
- TYPE: Parent
  VALUE: AUTH-L3-001
  ROLE: Implements

[COMPONENT]
UID: ARCH-C-006
TITLE: TokenCache
CA_LAYER: Adapter
STATEMENT: >>>
Caches verified tokens using LRU.
<<<
MODULE: src/auth/token_cache.c
RELATIONS:
- TYPE: Parent
  VALUE: AUTH-L3-002
  ROLE: Implements

[TEXT]
STATEMENT: >>>
**Data access domain (04-data-access)**
<<<

[COMPONENT]
UID: ARCH-C-007
TITLE: DataReadUseCase
CA_LAYER: UseCase
STATEMENT: >>>
Orchestrates DID read requests, coordinating the platform parts for authorization, resolution, UDS read, and JSON conversion.
<<<
MODULE: src/data/data_read_usecase.c
RELATIONS:
- TYPE: Parent
  VALUE: DATA-L2-002
  ROLE: Implements

[COMPONENT]
UID: ARCH-C-008
TITLE: DidResolver
CA_LAYER: Adapter
STATEMENT: >>>
Resolves a DID number to the address of the responsible ECU.
<<<
MODULE: src/data/did_resolver.c
RELATIONS:
- TYPE: Parent
  VALUE: DATA-L3-001
  ROLE: Implements

[COMPONENT]
UID: ARCH-C-009
TITLE: DataCache
CA_LAYER: Adapter
STATEMENT: >>>
Caches DID values with a TTL.
<<<
MODULE: src/data/data_cache.c
RELATIONS:
- TYPE: Parent
  VALUE: DATA-L3-002
  ROLE: Implements

[TEXT]
STATEMENT: >>>
**DTC domain (05-dtc-diagnostics)**
<<<

[COMPONENT]
UID: ARCH-C-010
TITLE: DtcParser
CA_LAYER: Adapter
STATEMENT: >>>
Parses the binary response of UDS 0x19 into a DTC list.
<<<
MODULE: src/dtc/dtc_parser.c
RELATIONS:
- TYPE: Parent
  VALUE: DTC-L3-001
  ROLE: Implements

[COMPONENT]
UID: ARCH-C-011
TITLE: FreezeFrameDecoder
CA_LAYER: Adapter
STATEMENT: >>>
Decodes a freeze frame payload into a list of (DID, value).
<<<
MODULE: src/dtc/freeze_frame_decoder.c
RELATIONS:
- TYPE: Parent
  VALUE: DTC-L3-002
  ROLE: Implements

[COMPONENT]
UID: ARCH-C-012
TITLE: SpeedReader
CA_LAYER: Adapter
STATEMENT: >>>
Acquires the vehicle speed periodically and provides the latest value (ASIL C certified task).
<<<
MODULE: src/dtc/speed_reader.c
RELATIONS:
- TYPE: Parent
  VALUE: DTC-L3-003
  ROLE: Implements

[COMPONENT]
UID: ARCH-C-013
TITLE: DtcHistoryStore
CA_LAYER: Entity
STATEMENT: >>>
Holds the DTC occurrence history in a ring buffer.
<<<
MODULE: src/dtc/dtc_history_store.c
RELATIONS:
- TYPE: Parent
  VALUE: DTC-L3-004
  ROLE: Implements

[TEXT]
STATEMENT: >>>
**OTA domain (06-sw-update)**
<<<

[COMPONENT]
UID: ARCH-C-014
TITLE: PackageDownloader
CA_LAYER: Adapter
STATEMENT: >>>
Downloads the update package in a resumable manner.
<<<
MODULE: src/swupdate/package_downloader.c
RELATIONS:
- TYPE: Parent
  VALUE: SWU-L3-001
  ROLE: Implements

[COMPONENT]
UID: ARCH-C-015
TITLE: SignatureVerifier
CA_LAYER: UseCase
STATEMENT: >>>
Verifies the signature (ECDSA P-256 / RSA-PSS 2048) of the update package.
<<<
MODULE: src/swupdate/signature_verifier.c
RELATIONS:
- TYPE: Parent
  VALUE: SWU-L3-002
  ROLE: Implements

[COMPONENT]
UID: ARCH-C-016
TITLE: FlashSectorWriter
CA_LAYER: Adapter
STATEMENT: >>>
Erases and writes flash sectors and verifies the write result with a CRC.
<<<
MODULE: src/swupdate/flash_sector_writer.c
RELATIONS:
- TYPE: Parent
  VALUE: SWU-L3-003
  ROLE: Implements

[COMPONENT]
UID: ARCH-C-017
TITLE: VehicleStateMonitor
CA_LAYER: Adapter
STATEMENT: >>>
Determines the driving state (vehicle speed, PKB, shift, IG) that is a precondition for a flash write (ASIL D certified).
<<<
MODULE: src/swupdate/vehicle_state_monitor.c
RELATIONS:
- TYPE: Parent
  VALUE: SWU-L3-004
  ROLE: Implements

[[/SECTION]]

[[SECTION]]
TITLE: 3.3 Module / File Structure (Module / File Structure)

[TEXT]
STATEMENT: >>>
.. code-block:: text

    src/
    |-- platform/                  # 07-common-platform (shared)
    |   |-- tls_terminator.c       # ARCH-C-001
    |   |-- scope_authorizer.c     # ARCH-C-002
    |   |-- uds_client.c           # ARCH-C-003
    |   `-- json_serializer.c      # ARCH-C-004
    |-- auth/                      # 03-auth
    |   |-- token_verifier.c       # ARCH-C-005
    |   `-- token_cache.c          # ARCH-C-006
    |-- data/                      # 04-data-access
    |   |-- data_read_usecase.c    # ARCH-C-007
    |   |-- did_resolver.c         # ARCH-C-008
    |   `-- data_cache.c           # ARCH-C-009
    |-- dtc/                       # 05-dtc-diagnostics
    |   |-- dtc_parser.c           # ARCH-C-010
    |   |-- freeze_frame_decoder.c # ARCH-C-011
    |   |-- speed_reader.c         # ARCH-C-012 (ASIL C)
    |   `-- dtc_history_store.c    # ARCH-C-013
    `-- swupdate/                  # 06-sw-update
        |-- package_downloader.c   # ARCH-C-014
        |-- signature_verifier.c   # ARCH-C-015
        |-- flash_sector_writer.c  # ARCH-C-016 (ASIL D)
        `-- vehicle_state_monitor.c# ARCH-C-017 (ASIL D)
<<<

[[/SECTION]]

[[SECTION]]
TITLE: 3.4 Domain Model (Domain Model)

[TEXT]
STATEMENT: >>>
**Class diagram 1: authenticated DID read** (each class's methods = the component's interface)

**This figure runs past 15 lines, so it lives in its own document** -> [LINK: DOC-FIG-ARCH-CLASS-CORE]
<<<

[TEXT]
STATEMENT: >>>
**Class diagram 2: DTC read / clear**

**This figure runs past 15 lines, so it lives in its own document** -> [LINK: DOC-FIG-ARCH-CLASS-ADAPTER]
<<<

[TEXT]
STATEMENT: >>>
**Class diagram 3: OTA update**

**This figure runs past 15 lines, so it lives in its own document** -> [LINK: DOC-FIG-ARCH-CLASS-FRAMEWORK]
<<<

[[/SECTION]]

[[SECTION]]
TITLE: 3.5 Behavior (Behavior)

[TEXT]
STATEMENT: >>>
**System sequence (representative slice: authenticated DID read, end to end)**

**This figure runs past 15 lines, so it lives in its own document** -> [LINK: DOC-FIG-ARCH-AUTH-SEQUENCE]

The representative sequences of the other domains (authentication flow, DTC guard, OTA state
machine) are placed in their respective requirement documents (03/05/06).
<<<

[[/SECTION]]

[[SECTION]]
TITLE: 3.6 Architecture Decision Records (Architecture Decision Records)

[TEXT]
STATEMENT: >>>
**ADR-001: Terminate SOVD at the gateway and bridge to UDS**

- Status: Accepted
- Context: Outside the vehicle is HTTP/REST (SOVD); inside is the existing UDS (ISO 14229).
- Decision: Terminate SOVD at the gateway ECU and relay to the internal ECUs over UDS.
- Consequences: Existing ECUs can be made SOVD-capable without changing them. The conversion layer is concentrated in the gateway.
<<<

[TEXT]
STATEMENT: >>>
**ADR-002: Separation of platform / feature (common platform)**

- Status: Accepted
- Context: UDS transport, authorization, TLS, and JSON are used by multiple features.
- Decision: Factor out the shared components into 07-common-platform, and have the features depend on it.
- Consequences: The dependency direction is unified to feature -> platform. Coupling between sibling features is eliminated. Convergence (N->1) appears in the traceability.
<<<

[TEXT]
STATEMENT: >>>
**ADR-003: Separate safety (ASIL) and security (CAL)**

- Status: Accepted
- Context: Attaching ASIL to security requirements such as authentication mixes up safety and security.
- Decision: Manage ASIL=ISO 26262 (safety) and CAL=ISO/SAE 21434 (security) in separate fields.
- Consequences: Pure security requirements carry ASIL=QM+CAL, safety-related ones carry ASIL, and ones that intersect both carry both.
<<<

[TEXT]
STATEMENT: >>>
**ADR-004: OTA uses A/B partitions + a state machine**

- Status: Accepted
- Context: Risks of writing while moving, tampering, and write failure.
- Decision: Write to the inactive side, switch over only on successful signature verification, and retain the previous version on failure. The state machine (06 §L1) structurally prohibits installation of unverified packages.
- Consequences: Rollback is easy. Update-time protection of safety-related ECUs is ensured at the requirement level (ASIL D).
<<<

[TEXT]
STATEMENT: >>>
**ADR-005: Components have a single responsibility (SRP); behavior is specified by tests**

- Status: Accepted
- Context: Loading responsibility and specification (behavior) into a single node makes individual verification and pass/fail untraceable.
- Decision: Limit components to a single responsibility (one sentence) plus responsibility-based naming, and express individual behaviors with test (10) scenarios (1 behavior = 1 scenario = 1 verdict).
- Consequences: Each behavior has an independent pass/fail and can be tracked down to gaps in a matrix. Implementation details (Table/Buffer, etc.) are excluded from naming.
<<<

[[/SECTION]]
