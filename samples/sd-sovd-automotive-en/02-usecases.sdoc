[DOCUMENT]
TITLE: SOVD Use Cases
UID: DOC-SOVD-USECASES
VERSION: 1.0

[GRAMMAR]
IMPORT_FROM_FILE: sovd-grammar.sgra

[TEXT]
STATEMENT: >>>
This document defines the **use cases** of the SOVD vehicle diagnostics system (usage
scenarios in which an actor uses the system to achieve a goal). Each UC realizes its
corresponding requirement (`01-stakeholder-requirements.sdoc`) via ``Parent`` and is
verified by an acceptance test (the AT series in `10-test-spec.sdoc`).

**Distinguishing requirements from use cases (IEEE 29148 / A-SPICE):** a "condition the
system must satisfy" is a requirement (EARS, `01-stakeholder-requirements.sdoc`), whereas
"how an actor uses it" belongs in this document (scenarios). Keep them as separate
artifacts and trace UC -> requirement (realization) and UC -> acceptance test
(verification).
<<<

[TEXT]
STATEMENT: >>>
**Actors**

.. list-table::
   :header-rows: 1
   :widths: 24 18 58

   * - Actor
     - RBAC role
     - Description / main concern
   * - Mechanic
     - ``Mechanic``
     - Diagnoses the vehicle remotely from the field or the workshop. Performs data reads and DTC retrieval / clearing.
   * - OEM engineer
     - ``OEMEngineer``
     - In addition to all diagnostic functions, can access DIDs containing personal data and perform OTA updates.
   * - Fleet operator
     - ``FleetOperator``
     - Remotely monitors the status of many vehicles in bulk (mainly read).
   * - OEM backend
     - (system)
     - External system responsible for token issuance, revocation-list distribution, update-package signing / distribution, and DTC master provisioning.
   * - Attacker (threat actor)
     - (none)
     - Attempts spoofing, eavesdropping, and tampering. The target defended against by authentication, authorization, and cryptography (UC-001).
<<<

[TEXT]
STATEMENT: >>>
**Use case diagram (actors and use cases)**

**This figure runs past 15 lines, so it lives in its own document** -> [LINK: DOC-FIG-USECASE-MAP]

UC-001 is the "authentication / authorization foundation" that all other UCs presuppose.
Attacker threats (spoofing, etc.) are defended in UC-001, and the OEM backend supplies the
trust anchor for tokens, revocation, and signatures.
<<<

[TEXT]
STATEMENT: >>>
**Use case list (from UC to the requirement it realizes)**

.. list-table::
   :header-rows: 1
   :widths: 10 32 28 30

   * - UC
     - Use case
     - Primary actor
     - Requirement realized
   * - UC-000
     - Whole system: remote diagnostics and update
     - All stakeholders
     - SYS-L0-001
   * - UC-001
     - Remote authenticated diagnostic access
     - Mechanic / OEM engineer
     - AUTH-L0-001 (03-auth)
   * - UC-002
     - Remote read of vehicle data
     - Mechanic / OEM / Fleet
     - DATA-L0-001 (04-data-access)
   * - UC-003
     - Fault diagnostics (retrieve / clear)
     - Mechanic / OEM engineer
     - DTC-L0-001 (05-dtc-diagnostics)
   * - UC-004
     - OTA remote software update
     - OEM engineer / OEM backend
     - SWU-L0-001 (06-sw-update)
<<<

[[SECTION]]
TITLE: UC-000 System-level Use Case

[REQUIREMENT]
UID: UC-000
TITLE: Remote diagnostics and update of the vehicle by authorized stakeholders
TYPE: UseCase
ASIL: QM
LAYER: L0_Stakeholder
STATEMENT: >>>
**Actors:** Mechanic / OEM engineer / Fleet operator (primary), Driver,
OEM backend, SOVD system.

**Preconditions:** The vehicle can connect to the cloud via the TCU, and stakeholders hold valid credentials.

**Main success scenario:**

1. An anomaly occurs in the vehicle (warning lamp lit, DTC recorded, fault reported).
2. A stakeholder accesses the SOVD system remotely and is authenticated (UC-001).
3. The system determines the authorization scope according to the role.
4. The stakeholder reads vehicle data (UC-002) and retrieves fault codes (UC-003) to investigate the cause.
5. If needed, the stakeholder clears fault codes (UC-003) or performs a remote software update (UC-004).
6. The system returns the result, and the vehicle's condition is understood and improved.

**Postconditions:** The vehicle's problem is diagnosed and addressed remotely, without bringing it into the workshop.

**Included use cases:** UC-001 authentication / UC-002 data / UC-003 DTC / UC-004 OTA.
<<<
VERIFICATION: >>>
The four primary use cases can be executed remotely by authorized stakeholders, and
unauthorized access is denied (confirmed by acceptance tests).
<<<
RELATIONS:
- TYPE: Parent
  VALUE: SYS-L0-001

[[/SECTION]]

[[SECTION]]
TITLE: UC-001 Authentication & Authorization

[REQUIREMENT]
UID: UC-001
TITLE: Remote authenticated diagnostic access by a mechanic
TYPE: UseCase
ASIL: QM
LAYER: L0_Stakeholder
STATEMENT: >>>
**Actors:** Mechanic (primary), Driver, OEM backend (token issuance), SOVD system.

**Preconditions:** The mechanic holds valid credentials, and the vehicle is reachable remotely.

**Main success scenario:**

1. The vehicle fails and the warning lamp lights up.
2. The driver asks a mechanic for remote diagnostics.
3. The mechanic authenticates with the SOVD client (OAuth 2.0 PKCE).
4. The system issues an access token (JWT).
5. The mechanic requests a diagnostic resource with the Bearer token attached.
6. The system verifies the token and scope, and grants access within the authorized range.

**Postconditions:** The mechanic can access vehicle diagnostics within the authorized scope.

**Alternative flows:** Unauthenticated -> denied with 401. Insufficient scope -> 403. Revoked token -> 401.
<<<
VERIFICATION: >>>
A GET of a diagnostic resource by an authenticated client returns HTTP 200 and the target
data can be retrieved.
<<<
RELATIONS:
- TYPE: Parent
  VALUE: AUTH-L0-001

[[/SECTION]]

[[SECTION]]
TITLE: UC-002 Vehicle Data Access

[REQUIREMENT]
UID: UC-002
TITLE: Remote read of vehicle data
TYPE: UseCase
ASIL: QM
LAYER: L0_Stakeholder
STATEMENT: >>>
**Actors:** Mechanic / OEM engineer (primary), SOVD system.

**Preconditions:** Authenticated and holding the read:did scope.

**Main success scenario:**

1. The mechanic wants to check the vehicle's current state (odometer, voltage, each ECU's temperature, etc.).
2. The mechanic specifies the target DID and requests a read.
3. The system verifies the scope.
4. The system resolves the DID to the responsible ECU and translates it into a UDS ReadDataByIdentifier.
5. The ECU returns the value.
6. The system converts it into ASAM SOVD JSON and returns it to the mechanic.

**Postconditions:** The mechanic can understand the vehicle data.

**Alternative flows:** A Mechanic accessing a personal-data DID -> 403. Periodic subscription, snapshot, and
bulk transfer follow the same authorization flow.
<<<
VERIFICATION: >>>
A representative set of DIDs can be retrieved by an authorized client, and unauthorized items are not returned.
<<<
RELATIONS:
- TYPE: Parent
  VALUE: DATA-L0-001

[[/SECTION]]

[[SECTION]]
TITLE: UC-003 Fault Diagnostics (DTC)

[REQUIREMENT]
UID: UC-003
TITLE: Fault diagnostics (retrieve / clear)
TYPE: UseCase
ASIL: QM
LAYER: L0_Stakeholder
STATEMENT: >>>
**Actors:** Mechanic (primary), SOVD system.

**Preconditions:** Authenticated and holding the read:dtc (retrieve) / write:dtc (clear) scope.

**Main success scenario:**

1. The mechanic wants to investigate the fault cause of a vehicle whose warning lamp is lit.
2. The mechanic requests the list of fault codes (DTCs).
3. The system aggregates each ECU's DTCs via UDS 0x19 and returns them with their status.
4. The mechanic identifies the cause and performs the repair.
5. After the repair, the mechanic requests clearing of the target DTC.
6. The system confirms the vehicle speed is zero and clears it via UDS 0x14.

**Postconditions:** The fault codes are retrieved and (if stationary) cleared.

**Alternative flows:** Clearing while the vehicle is moving -> denied with 409. Freeze-frame retrieval follows the same flow.
<<<
VERIFICATION: >>>
Representative DTCs can be retrieved together with their status (active/pending/confirmed/permanent).
<<<
RELATIONS:
- TYPE: Parent
  VALUE: DTC-L0-001

[[/SECTION]]

[[SECTION]]
TITLE: UC-004 Software Update (OTA)

[REQUIREMENT]
UID: UC-004
TITLE: OTA remote software update
TYPE: UseCase
ASIL: QM
LAYER: L0_Stakeholder
STATEMENT: >>>
**Actors:** OEM engineer / OEM backend (primary), Driver, SOVD system.

**Preconditions:** A signed update package is prepared, and the vehicle can receive the update.

**Main success scenario:**

1. The OEM wants to distribute a defect-fix software to the vehicle.
2. The OEM backend distributes the signed update package.
3. The system downloads the package.
4. The system verifies the signature.
5. The system confirms the driving state (stationary, shift in Park, parking brake) and writes to the inactive side.
6. The new version boots via the bootloader switch, and the progress is notified to the driver.

**Postconditions:** The ECU runs on the new software version.

**Alternative flows:** Signature verification failure -> discard. While moving -> writing is deferred. Write failure -> rollback to the previous version.
<<<
VERIFICATION: >>>
Distribution -> application -> progress check of a signed package can be performed as a
single sequence, and after application it boots on the new version.
<<<
RELATIONS:
- TYPE: Parent
  VALUE: SWU-L0-001

[[/SECTION]]
