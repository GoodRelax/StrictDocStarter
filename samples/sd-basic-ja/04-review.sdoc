[DOCUMENT]
TITLE: レビューの進め方
UID: DOC-REVIEW
VERSION: 1.0

[GRAMMAR]
IMPORT_FROM_FILE: basic.sgra

[TEXT]
STATEMENT: >>>
**本書は、 レビューの結果をどこにどう書くかを伝える。**

**この一式は、 指摘を要求そのものに書く。** 指摘を別のノードとして起こし、
関係で要求へ結ぶやり方もあるが、 採らない。 理由は 3 章にある。

要求に足したのは次の 3 項目である。 `basic.sgra` が `REQUIREMENT` に宣言して
いる。

==============  ===========================================  ====================
項目            中身                                         書く人
==============  ===========================================  ====================
REVIEW_STATUS   レビューの状態。 **必須**                    レビューアと書いた人
REVIEW_COMMENT  指摘の内容。 何が問題か                      レビューア
REVIEW_ACTION   対策として何をしたか。 直さないならその理由  書いた人
==============  ===========================================  ====================
<<<

[[SECTION]]
TITLE: 状態の 5 つ

[TEXT]
STATEMENT: >>>
::

    - TITLE: REVIEW_STATUS
      TYPE: SingleChoice(NotReviewed, NoFinding, Open, Fixed, WontFix)
      REQUIRED: True

===========  ===============================  ==============  =====================
値           意味                             REVIEW_COMMENT  REVIEW_ACTION
===========  ===============================  ==============  =====================
NotReviewed  まだ誰も見ていない               空              空
NoFinding    見た。 指摘なし                  空              空
Open         **指摘あり・未対応**             **要る**        空
Fixed        指摘に対応した                   **要る**        **要る**
WontFix      検討して **対応しないと決めた**  **要る**        **要る (理由を書く)**
===========  ===============================  ==============  =====================

**REQUIRED: True にしてある。** 書き忘れると `strictdoc export` が止まるので、
「レビュー欄が無い要求」が生まれない。 **NotReviewed を明示的に置いたのは
このためである** — 欄が無いことに意味を持たせると、 書き忘れと区別が付かなく
なる。

**WontFix は Fixed と同じくらい正当な終わり方である。** 指摘を受けて検討し、
直さないと決めたなら、 **その理由を `REVIEW_ACTION` に残す。** 理由が残って
いれば、 半年後に同じ指摘が出たときに議論をやり直さずに済む。

**Rejected という語を使わない** のは、 指摘そのものを退けたように読めるため
である。 受け取ったうえでの判断だと分かる語を選んだ。
<<<

[[/SECTION]]

[[SECTION]]
TITLE: 書き方

[TEXT]
STATEMENT: >>>
**`.sdoc` では 8 項目を文法の宣言順にそのまま並べる。** `.md` のように
「1 行の項目は上のかたまり、 段落の項目は後ろ」という区別は無い。

::

    [REQUIREMENT]
    UID: SYS-002
    STATUS: Approved
    TITLE: 想定外の入力の拒否
    REVIEW_STATUS: Fixed
    STATEMENT: >>>
    もし入力ファイルが利用者の指定した形式でないならば、 本ツールは、
    変換を行わないこと。
    <<<
    REVIEW_COMMENT: >>>
    壊れたファイルを渡されたときの扱いが決まっていなかった。
    <<<
    REVIEW_ACTION: >>>
    SW-002 に読み取り失敗も検査の対象として足した。
    <<<

**★ 順を変えてはならない。** `basic.sgra` が宣言した順と `.sdoc` に書いた順が
食い違うと、 export が次のように止まる。 **`Hint:` の行が問題のフィールド名と
文法側の並びを教えるので、 直し方はその場で分かる** (実測)。

::

    Semantic error: Wrong field order for requirement: [UID, STATUS, TITLE, ...]
    Hint: Problematic field: RATIONALE. Compare with the document grammar: [...]

**★ 綴りは文法のとおりに書く。** `Review_comment:` は
`Invalid requirement field` で落ちる。

**★ 書き忘れも止まる。** `REVIEW_STATUS` は `REQUIRED: True` なので、
落とすと `Node is missing a field that is required by grammar: REVIEW_STATUS`
で止まる (実測)。
<<<

[[/SECTION]]

[[SECTION]]
TITLE: なぜ別ノードにしないか

[TEXT]
STATEMENT: >>>
指摘を `FINDING` のような独自の型として起こし、 `ROLE: Reviews` で要求へ結ぶ
やり方もある。 **この一式は以前それを採っていた。 やめた理由は 1 つである。**

**要求の一覧から状態が見えないからである。** 関係として結ぶと、 要求の側には
「指摘が在る」ことしか出ない。 **未対応なのか対応済みなのかは、 指摘を開くまで
分からない。** レビューで知りたいのはまさにそこである。

要求の項目にすると、 **Document / Table / Traceability の 3 つのビューすべてに
出る** (実測)。 とくに Table ビューは列の取捨選択と並べ替えができるので、
**「Open だけを並べる」がその場で終わる。**

**捨てたものもある。**

============================  =====================  ======================
観点                          要求の項目 (この一式)  別ノード + 関係
============================  =====================  ======================
要求の一覧から状態が見える    **○**                  ✗
1 つの要求に指摘を複数        ✗ **1 件だけ**         **○**
指摘ごとの UID と履歴         ✗                      **○**
プロジェクト全体の行列に出る  ✗                      **○**
書く手間                      **3 行足すだけ**       別文書にノードを起こす
============================  =====================  ======================

**指摘を何件も積み、 1 件ずつ追跡する必要があるなら、 別ノードのほうが向く。**
そのときは `basic.sgra` に型を足す。 **足すのは文法ファイルであり、 個別の
文書ではない。**
<<<

[[/SECTION]]

[[SECTION]]
TITLE: 溜まった状態を数える

[TEXT]
STATEMENT: >>>
**画面で数えるより JSON を引くほうが速い。** JSON の出し方と jq の使い方は
`00-guide-for-human.sdoc` の「JSON で引く」の章にある。 未対応の指摘を全部
出すクエリはこれである。

::

    .DOCUMENTS[] | recurse(.NODES[]?)
    | select(.REVIEW_STATUS == "Open")
    | .UID + "  " + .TITLE

状態ごとの件数はこれで出る。

::

    [.DOCUMENTS[] | recurse(.NODES[]?) | select(.REVIEW_STATUS?) | .REVIEW_STATUS]
    | group_by(.) | map({(.[0]): length}) | add

**まだ誰も見ていない要求** を出すには `NotReviewed` を選ぶ。
<<<

[[/SECTION]]

[[SECTION]]
TITLE: この一式の現状

[TEXT]
STATEMENT: >>>
`01-upper.sdoc` と `02-lower.sdoc` の 7 件が、 5 つの状態を一通り見せている。

=======  =============  ========================
UID      REVIEW_STATUS  何の例か
=======  =============  ========================
SYS-001  NoFinding      見たが指摘なし
SYS-002  Fixed          指摘して直した
SYS-003  Open           **指摘あり・未対応**
SW-001   NoFinding
SW-002   NoFinding
SW-003   NotReviewed    **まだ見ていない**
SW-004   WontFix        検討して直さないと決めた
=======  =============  ========================

**テストケースには `REVIEW_STATUS` が無い。** `basic.sgra` は `REQUIREMENT` に
だけ宣言している。 テストケースは代わりに `TEST_RESULT` / `ISSUE_KEY` /
`TEST_REMARK` を持つ — 書き方は `03-tests.sdoc` にある。 テストの文面そのものも
レビューの対象にするなら、 `TEST_CASE` にも同じ 3 項目を足す。
<<<

[[/SECTION]]
