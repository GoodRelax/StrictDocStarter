[DOCUMENT]
TITLE: 基本 - レビュー指摘
UID: DOC-REVIEW
VERSION: 1.0

[GRAMMAR]
IMPORT_FROM_FILE: basic.sgra

[TEXT]
STATEMENT: >>>
**この文書が `basic.sgra` を置いてある理由そのものである。**

レビュー指摘も StrictDoc の標準概念ではない。 組み込みの `[REQUIREMENT]` に
無理に押し込むと「重大度」や「対処状況」の置き場が無い。 そこで
`basic.sgra` に `FINDING` というノード型を足し、 `SEVERITY` と
`RESOLUTION` を専用のフィールドとして宣言してある。

**選択肢は文法側で固定する。** `SingleChoice(Major, Minor, Question)` と
書いておけば、 綴り違いはその場で解析エラーになり、 ブラウザの編集画面では
選択肢のドロップダウンになる。 自由記入にしてはならない。

対象の要求へは `ROLE: Reviews` で結ぶ。 これで指摘は要求の画面にも並んで
表示され、 JSON からも 1 クエリで取り出せる。
<<<

[FINDING]
UID: RV-001
TITLE: SW-002 の検査方法が決まっていない
SEVERITY: Major
RESOLUTION: Open
STATEMENT: >>>
「形式を検査する」の判定方法が書かれていない。 拡張子で見るのか中身を見るのかで
実装も TC-002 の手順も変わる。 どちらかに決めること。
<<<
RELATIONS:
- TYPE: Parent
  VALUE: SW-002
  ROLE: Reviews

[FINDING]
UID: RV-002
TITLE: SYS-003 に上書きを許す手段が無い
SEVERITY: Question
RESOLUTION: Open
STATEMENT: >>>
既定を安全側に倒すのは妥当だが、 意図して上書きしたい利用者の逃げ道が無い。
明示的な指定を設けるかどうかが未決である。
<<<
RELATIONS:
- TYPE: Parent
  VALUE: SYS-003
  ROLE: Reviews
