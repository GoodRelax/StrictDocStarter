[DOCUMENT]
TITLE: 上位要求
UID: DOC-UPPER
VERSION: 1.0

[GRAMMAR]
IMPORT_FROM_FILE: basic.sgra

[TEXT]
STATEMENT: >>>
本書に書くのは **何を作るか** だけである。 どう作るかは `02-lower.sdoc` に
分けてある。

この段落は `[TEXT]` であり UID を持たない。 **地の文には UID を付けない。**
付けるかどうかの基準は 1 つだけである — **後から名前で引きたいなら付ける。**
説明や前置きは引かないので付けない。
<<<

[[SECTION]]
TITLE: 要求の書き方 - EARS

[TEXT]
STATEMENT: >>>
本書と `02-lower.sdoc` の要求は、 すべて **EARS** の 5 つの型のいずれかで
書いてある。 EARS は要求文の形を 5 つに絞る書き方であり、 条件の書き忘れと、
1 つの文へ複数の要求を詰め込むことを防ぐ。

=======================================  ==========================================================  ===================================================
型                                       形                                                          原型 (英語)
=======================================  ==========================================================  ===================================================
遍在型 (Ubiquitous)                      〈システム〉は、 〈応答〉すること。                         The <system> shall <response>.
事象駆動型 (Event-driven)                〈トリガ〉したとき、 〈システム〉は、 〈応答〉すること。    WHEN <trigger>, the <system> shall <response>.
状態駆動型 (State-driven)                〈状態〉の間、 〈システム〉は、 〈応答〉すること。          WHILE <state>, the <system> shall <response>.
望ましくない挙動型 (Unwanted behaviour)  もし〈条件〉ならば、 〈システム〉は、 〈応答〉すること。    IF <condition>, THEN the <system> shall <response>.
任意機能型 (Optional feature)            〈機能〉を備える場合、 〈システム〉は、 〈応答〉すること。  WHERE <feature>, the <system> shall <response>.
=======================================  ==========================================================  ===================================================

**英語の原型を併記したのは、 EARS の資料がほぼ英語で書かれているためである。**
型を見分ける手掛かりは、 英語では文頭の WHEN / WHILE / IF / WHERE という
1 語であり、 日本語では 「〜したとき」 / 「〜の間」 / 「もし〜ならば」 /
「〜を備える場合」 という語尾である。 **どちらも文の先頭に置く。**

**shall は 「〜すること。」 に当たる。** 英語の EARS が shall を要求、
will を事実の記述、 should を推奨として使い分けるのと同じ区別を、 日本語では
「〜すること。」 と 「〜する。」 と 「〜が望ましい。」 で付ける。

**条件は主語より先に書く。** これが EARS の要点である。 主語を先頭に置いて
「本ツールは、 〜の場合、 〜すること。」 と書くと、 読む側は条件に行き着くまで
主語を抱えたままになり、 条件の抜けにも気づけない。 条件を先に出せば、
**その要求がいつ効くのかが文頭で決まる。**

**この一式は EARS 専用のフィールドをあえて持たない。** 型は `STATEMENT` の文
そのものに現れる。 型名を別のフィールドに書くと、 フィールドと本文がずれた
ときにどちらを信じるのかを決められなくなる。

`samples/md-basic-ja` が同じ 7 件を `.md` で書いている。 **文面は 1 文字も
違わない。**
<<<

[[SECTION]]
TITLE: 複合型 - 型を重ねる

[TEXT]
STATEMENT: >>>
**上の 5 つを重ねた 6 つめの型がある。** EARS の原典はこれを **複合型
(Complex)** と呼ぶ。 条件が 2 つ以上あるときに使う。

::

    WHERE <feature>, WHILE <state>, WHEN <trigger>, the <system> shall <response>.

日本語ではこうなる。

::

    〈機能〉を備える場合、 〈状態〉の間に〈トリガ〉したとき、
    〈システム〉は、 〈応答〉すること。

**重ねる順が決まっている。** 外側から内側へ、 **WHERE → WHILE → WHEN
(または IF)** の順に置く。 原典は複合型の雛形を
`While <precondition(s)>, When <trigger>, the <system name> shall <system response>`
と書いており、 **状態が先、 トリガが後** である。

==========================  ===============================================
重ねるもの                  意味
==========================  ===============================================
WHERE (〜を備える場合)      その機能を積んだ製品にだけ効く。 製品の構成の話
WHILE (〜の間)              その状態が続いている間だけ効く。 時間の幅を持つ
WHEN (〜したとき)           その瞬間に効く。 時間の幅を持たない
IF ... THEN (もし〜ならば)  望ましくない入力や状況に効く
==========================  ===============================================

**★ 重ねるのは 2 つまでにすること。** 3 つ重ねた文は、 読む側が条件の
組み合わせを数え上げられなくなる。 **3 つ要るなら、 それは要求が 2 つに
分かれる合図である。**

この一式には複合型の例が無い。 対象が単純で、 重ねる必要が出なかったためである。
**必要になったときだけ使うこと** — 型を増やすこと自体には価値が無い。
<<<

[[/SECTION]]

[[SECTION]]
TITLE: 原典

[TEXT]
STATEMENT: >>>
**EARS の定義は 1 つの出典に集約されている。** 迷ったらここを読むこと。

- **EARS の公式ページ** — https://alistairmavin.com/ears/
  考案者の Alistair Mavin による解説。 6 つの型の雛形と例が載っている。
  **本書の日本語の言い回しは、 このページの英語の雛形をなぞったものである。**
- 初出は 2009 年の論文である。 Mavin, Wilkinson, Harwood, Novak,
  "Easy Approach to Requirements Syntax (EARS)",
  17th IEEE International Requirements Engineering Conference (RE'09),
  pp. 317-322.
<<<

[[/SECTION]]

[[/SECTION]]

[REQUIREMENT]
UID: SYS-001
STATUS: Approved
TITLE: ファイルの変換
REVIEW_STATUS: NoFinding
STATEMENT: >>>
本ツールは、 利用者が指定した入力ファイルを、 利用者が指定した出力形式へ
変換すること。
<<<
RATIONALE: >>>
本ツールの存在理由そのものである。 これを外すと他の要求が意味を失う。
<<<

[REQUIREMENT]
UID: SYS-002
STATUS: Approved
TITLE: 想定外の入力の拒否
REVIEW_STATUS: Fixed
STATEMENT: >>>
もし入力ファイルが利用者の指定した形式でないならば、 本ツールは、
変換を行わないこと。
<<<
REVIEW_COMMENT: >>>
下位要求 SW-002 が、 変換を拒む条件を「検査する」という手順としてしか
書いておらず、 どの入力を拒むのかを文の先頭から読み取れなかった。
<<<
REVIEW_ACTION: >>>
SW-002 を、 条件から始まる形に書き直した。 拒む入力が文の先頭で分かる。
<<<

[REQUIREMENT]
UID: SYS-003
STATUS: Reviewed
TITLE: 既存ファイルの保護
REVIEW_STATUS: Open
STATEMENT: >>>
もし出力先に同名のファイルが既にあるならば、 本ツールは、 そのファイルを
上書きしないこと。
<<<
RATIONALE: >>>
無警告で既存ファイルを潰すと、 利用者は取り返しのつかない操作に気づけない。
既定は安全側に倒す。
<<<
REVIEW_COMMENT: >>>
「上書きしない」とだけ書いてあるが、 同名のファイルがあったときに何を
するのかが決まっていない。 中断か、 別名か。
<<<
