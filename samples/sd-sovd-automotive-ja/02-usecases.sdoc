[DOCUMENT]
TITLE: SOVD ユースケース (Use Cases)
UID: DOC-SOVD-USECASES
VERSION: 1.0

[GRAMMAR]
IMPORT_FROM_FILE: sovd-grammar.sgra

[TEXT]
STATEMENT: >>>
本書は SOVD 車両診断システムの **ユースケース** (アクターがシステムを使って目標を達成する
利用シナリオ) を定義する。 各 UC は対応する要求 (`01-stakeholder-requirements.sdoc`) を
``Parent`` で実現し、 受入テスト (`10-test-spec.sdoc` の AT 系) で検証される。

**要求と UC の区別 (IEEE 29148 / A-SPICE):** 「システムが満たす条件」は要求 (EARS、
`01-stakeholder-requirements.sdoc`)、 「アクターがどう使うか」は本書 (シナリオ)。 別物として
分離し、 UC → 要求 (実現) と UC → 受入テスト (検証) でトレースする。
<<<

[TEXT]
STATEMENT: >>>
**アクター (Actors)**

.. list-table::
   :header-rows: 1
   :widths: 24 18 58

   * - アクター
     - RBAC ロール
     - 説明 / 主な関心
   * - 整備士
     - ``Mechanic``
     - 出先・工場から遠隔で車両を診断する。 データ読出・DTC 取得 / クリアを行う。
   * - OEM エンジニア
     - ``OEMEngineer``
     - 全診断機能に加え、 個人情報を含む DID へのアクセスや OTA 更新の実施が可能。
   * - フリート運用者
     - ``FleetOperator``
     - 多数車両の状態を遠隔で一括監視する (主に読み取り)。
   * - OEM バックエンド
     - (システム)
     - トークン発行・失効リスト配信・更新パッケージの署名 / 配信・DTC マスタ提供を担う外部システム。
   * - 攻撃者 (脅威アクター)
     - (なし)
     - なりすまし・盗聴・改ざんを試みる。 認証・認可・暗号 (UC-001) で防御する対象。
<<<

[TEXT]
STATEMENT: >>>
**ユースケース図 (アクターとユースケース)**

**この図は 15 行を超えるので別文書にしてある** → [LINK: DOC-FIG-USECASE-MAP]

UC-001 は全 UC の前提となる「認証・認可の土台」。 攻撃者の脅威 (なりすまし等) は UC-001 で
防御し、 OEM バックエンドがトークン・失効・署名の信頼基盤を供給する。
<<<

[TEXT]
STATEMENT: >>>
**ユースケース一覧 (UC から実現する要求へ)**

.. list-table::
   :header-rows: 1
   :widths: 10 32 28 30

   * - UC
     - ユースケース
     - 主アクター
     - 実現する要求
   * - UC-000
     - システム全体: 遠隔診断・更新
     - 全関係者
     - SYS-L0-001
   * - UC-001
     - 遠隔・認証付き診断アクセス
     - 整備士 / OEM エンジニア
     - AUTH-L0-001 (03-auth)
   * - UC-002
     - 車両データの遠隔読み取り
     - 整備士 / OEM / フリート
     - DATA-L0-001 (04-data-access)
   * - UC-003
     - 故障診断 (取得・クリア)
     - 整備士 / OEM エンジニア
     - DTC-L0-001 (05-dtc-diagnostics)
   * - UC-004
     - OTA 遠隔ソフトウェア更新
     - OEM エンジニア / OEM バックエンド
     - SWU-L0-001 (06-sw-update)
<<<

[[SECTION]]
TITLE: UC-000 システム全体 (System-level Use Case)

[REQUIREMENT]
UID: UC-000
TITLE: 認可された関係者による車両の遠隔診断・更新
TYPE: UseCase
ASIL: QM
LAYER: L0_Stakeholder
STATEMENT: >>>
**アクター:** 整備士 / OEM エンジニア / フリート運用者 (主)、 ドライバー、
OEM バックエンド、 SOVD システム。

**事前条件:** 車両が TCU 経由でクラウドに接続でき、 関係者が有効な資格情報を持つ。

**主成功シナリオ:**

1. 車両に異常が生じる (警告灯点灯・DTC 記録・不具合報告)。
2. 関係者が遠隔から SOVD システムへアクセスし、 認証を受ける (UC-001)。
3. システムが役割に応じた認可範囲を判定する。
4. 関係者が車両データの読み取り (UC-002) や故障コードの取得 (UC-003) を行い、 原因を調べる。
5. 必要に応じて、 故障コードのクリア (UC-003) やソフトウェアの遠隔更新 (UC-004) を実施する。
6. システムが結果を返し、 車両の状態が把握・改善される。

**事後条件:** 工場へ入庫せずに、 車両の問題が遠隔で診断・対処される。

**含まれるユースケース:** UC-001 認証 / UC-002 データ / UC-003 DTC / UC-004 OTA。
<<<
VERIFICATION: >>>
4 つの主要ユースケースが認可された関係者により遠隔で実行でき、 未認可のアクセスは
拒否されること (受入テストで確認)。
<<<
RELATIONS:
- TYPE: Parent
  VALUE: SYS-L0-001

[[/SECTION]]

[[SECTION]]
TITLE: UC-001 認証・認可 (Authentication & Authorization)

[REQUIREMENT]
UID: UC-001
TITLE: 整備士による遠隔・認証付き診断アクセス
TYPE: UseCase
ASIL: QM
LAYER: L0_Stakeholder
STATEMENT: >>>
**アクター:** 整備士 (主)、 ドライバー、 OEM バックエンド (トークン発行)、 SOVD システム。

**事前条件:** 整備士が有効な資格情報を持ち、 車両が遠隔到達可能である。

**主成功シナリオ:**

1. 車両が故障し、 警告灯が点く。
2. ドライバーが整備士に遠隔診断を依頼する。
3. 整備士が SOVD クライアントで認証する (OAuth 2.0 PKCE)。
4. システムがアクセストークン (JWT) を発行する。
5. 整備士が Bearer トークンを付けて診断リソースを要求する。
6. システムがトークンとスコープを検証し、 認可された範囲でアクセスを許可する。

**事後条件:** 整備士が認可された範囲で車両診断にアクセスできる。

**代替フロー:** 未認証 → 401 で拒否。 スコープ不足 → 403。 失効トークン → 401。
<<<
VERIFICATION: >>>
認証済みクライアントで診断リソースの GET が HTTP 200 を返し、 対象データが
取得できること。
<<<
RELATIONS:
- TYPE: Parent
  VALUE: AUTH-L0-001

[[/SECTION]]

[[SECTION]]
TITLE: UC-002 車両データアクセス (Vehicle Data Access)

[REQUIREMENT]
UID: UC-002
TITLE: 車両データの遠隔読み取り
TYPE: UseCase
ASIL: QM
LAYER: L0_Stakeholder
STATEMENT: >>>
**アクター:** 整備士 / OEM エンジニア (主)、 SOVD システム。

**事前条件:** 認証済みで read:did スコープを持つ。

**主成功シナリオ:**

1. 整備士が車両の現在状態 (走行距離・電圧・各 ECU 温度等) を確認したい。
2. 整備士が対象の DID を指定して読み取りを要求する。
3. システムがスコープを検証する。
4. システムが DID を担当 ECU へ解決し、 UDS ReadDataByIdentifier へ変換する。
5. ECU が値を返す。
6. システムが ASAM SOVD JSON に変換して整備士へ返す。

**事後条件:** 整備士が車両データを把握できる。

**代替フロー:** 個人情報 DID へ Mechanic がアクセス → 403。 周期購読・スナップショット・
バルク転送も同じ認可フローに従う。
<<<
VERIFICATION: >>>
認可されたクライアントで代表的な DID 群が取得でき、 未認可の項目は返らないこと。
<<<
RELATIONS:
- TYPE: Parent
  VALUE: DATA-L0-001

[[/SECTION]]

[[SECTION]]
TITLE: UC-003 故障診断 (DTC)

[REQUIREMENT]
UID: UC-003
TITLE: 故障診断 (取得・クリア)
TYPE: UseCase
ASIL: QM
LAYER: L0_Stakeholder
STATEMENT: >>>
**アクター:** 整備士 (主)、 SOVD システム。

**事前条件:** 認証済みで read:dtc (取得) / write:dtc (クリア) スコープを持つ。

**主成功シナリオ:**

1. 整備士が、 警告灯の点いた車両の故障原因を調べたい。
2. 整備士が故障コード (DTC) 一覧を要求する。
3. システムが UDS 0x19 で各 ECU の DTC を集約し、 ステータス付きで返す。
4. 整備士が原因を特定し、 修理を行う。
5. 修理後、 整備士が対象 DTC のクリアを要求する。
6. システムが車速ゼロを確認し、 UDS 0x14 でクリアする。

**事後条件:** 故障コードが取得され、 (停車中なら) クリアされる。

**代替フロー:** 走行中のクリア → 409 で拒否。 フリーズフレーム取得も同フロー。
<<<
VERIFICATION: >>>
代表的な DTC が、 status (active/pending/confirmed/permanent) 付きで取得できること。
<<<
RELATIONS:
- TYPE: Parent
  VALUE: DTC-L0-001

[[/SECTION]]

[[SECTION]]
TITLE: UC-004 ソフトウェア更新 (OTA)

[REQUIREMENT]
UID: UC-004
TITLE: OTA 遠隔ソフトウェア更新
TYPE: UseCase
ASIL: QM
LAYER: L0_Stakeholder
STATEMENT: >>>
**アクター:** OEM エンジニア / OEM バックエンド (主)、 ドライバー、 SOVD システム。

**事前条件:** 署名付きの更新パッケージが用意され、 車両が更新を受け取れる。

**主成功シナリオ:**

1. OEM が不具合修正ソフトを車両へ配信したい。
2. OEM バックエンドが署名付き更新パッケージを配信する。
3. システムがパッケージをダウンロードする。
4. システムが署名を検証する。
5. システムが走行状態 (停車・シフト P・パーキングブレーキ) を確認し、 非アクティブ側へ書き込む。
6. ブートローダ切替で新バージョンが起動し、 進捗をドライバーへ通知する。

**事後条件:** ECU が新しいソフトウェアバージョンで動作する。

**代替フロー:** 署名検証失敗 → 破棄。 走行中 → 書込延期。 書込失敗 → 旧版へロールバック。
<<<
VERIFICATION: >>>
署名付きパッケージの配信 → 適用 → 進捗確認が一連で行え、 適用後に新バージョンで
起動すること。
<<<
RELATIONS:
- TYPE: Parent
  VALUE: SWU-L0-001

[[/SECTION]]
