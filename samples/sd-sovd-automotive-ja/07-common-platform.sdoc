[DOCUMENT]
TITLE: SOVD 共通プラットフォーム 要求仕様 (Common Platform / Shared Components)
UID: DOC-SOVD-PLATFORM
VERSION: 1.0

[GRAMMAR]
IMPORT_FROM_FILE: sovd-grammar.sgra

[TEXT]
STATEMENT: >>>
本書は、 複数の機能ドメイン (03-auth / 04-data-access / 05-dtc-diagnostics /
06-sw-update) が **共通で再利用する** ゲートウェイ基盤のユニット要求を集約する。
各機能ドメインの要求 (L2_ECU_SW) は、 ここに定義する基盤ユニットへ収束 (N→1) する。

**依存方向:** 機能 → 基盤 の一方向。 これにより「ある機能が別の機能 (兄弟) の文書に
依存する」 不健全な結合を避け、 共有部品の責務と所在を一箇所に固定する
(Clean Architecture の依存方向・SoC/SRP、 A-SPICE のプラットフォーム要素管理に対応)。

共有の前付け (用語・表記規約・ASIL/CAL の使い分け) は `00-overview.sdoc` を参照。
<<<

[TEXT]
STATEMENT: >>>
**コンポーネント収束図 (機能 → 共通基盤)**

**この図は 15 行を超えるので別文書にしてある** → [LINK: DOC-FIG-PLATFORM-SHARED]

注: TlsTerminator は全機能ドメインの外部通信を終端するが、 TLS 要求は代表として
03-auth (AUTH-L1-005 / AUTH-L2-004) に集約されるため、 図では Auth からの依存のみを
示す。 なお 06-sw-update は独自の更新系ユニット群を持つため、 共通基盤への収束は
図に現れない。
<<<

[[SECTION]]
TITLE: 共通プラットフォーム ユニット (Shared Platform Units)

[REQUIREMENT]
UID: PLAT-L3-001
TITLE: UdsClient ユニット (共有 UDS トランスポート)
TYPE: Functional
ASIL: QM
LAYER: L3_Unit
STATEMENT: >>>
UdsClient ユニットは、 ISO 14229-1 準拠の UDS フレーム送受信を担い、 タイムアウト・
リトライ・NRC ハンドリングを提供すること。
<<<
RATIONALE: >>>
ゲートウェイ内の共有 UDS トランスポート。 データアクセスの ReadDataByIdentifier
ブリッジ (DATA-L2-002) と、 DTC の 0x19 読出 (DTC-L2-001) ・0x14 クリア (DTC-L2-003)
の双方から再利用される。 1 つのユニットが複数ドメインの上位要求を実現する収束 (N→1)。
<<<
RELATIONS:
- TYPE: Parent
  VALUE: DATA-L2-002
- TYPE: Parent
  VALUE: DTC-L2-001
- TYPE: Parent
  VALUE: DTC-L2-003

[REQUIREMENT]
UID: PLAT-L3-002
TITLE: ScopeAuthorizer ユニット (共有 認可)
TYPE: Functional
ASIL: QM
CAL: CAL3
LAYER: L3_Unit
STATEMENT: >>>
ScopeAuthorizer ユニットは、 (required_scope, token_scopes) を入力として許可または
拒否を返すこと。 拒否したとき、 ScopeAuthorizer ユニットは、 理由コード
(insufficient_scope / expired 等) を返すこと。
<<<
RATIONALE: >>>
認証 (AUTH-L2-003) と車両データアクセス (DATA-L2-006) の双方でスコープ検証に
再利用される共有ユニット。 1 つの下位要求が複数ドメインの上位要求を実現する収束 (N→1)。
<<<
RELATIONS:
- TYPE: Parent
  VALUE: AUTH-L2-003
- TYPE: Parent
  VALUE: DATA-L2-006

[REQUIREMENT]
UID: PLAT-L3-003
TITLE: TlsTerminator ユニット (共有 TLS 終端)
TYPE: Functional
ASIL: QM
CAL: CAL3
LAYER: L3_Unit
STATEMENT: >>>
TlsTerminator ユニットは、 OpenSSL ベースの TLS 終端を提供すること。
起動したとき、 TlsTerminator ユニットは、 信頼ストアをロードすること。
<<<
RATIONALE: >>>
全機能ドメインの外部通信を終端する横断的なセキュリティ基盤。 明示的な TLS 要求は
03-auth (AUTH-L1-005 / AUTH-L2-004) にあり、 本ユニットがそれを実装する。
<<<
VERIFICATION: >>>
ハンドシェイク失敗時に、 上位へエラーイベントが通知されること。
<<<
RELATIONS:
- TYPE: Parent
  VALUE: AUTH-L2-004

[REQUIREMENT]
UID: PLAT-L3-004
TITLE: JsonSerializer ユニット (共有 応答エンコード)
TYPE: Functional
ASIL: QM
LAYER: L3_Unit
STATEMENT: >>>
JsonSerializer ユニットは、 診断データ (DID 値: 整数・浮動小数・文字列・バイト列、
DTC 等) を ASAM SOVD JSON 形式に変換すること。
<<<
RATIONALE: >>>
SOVD の JSON 応答エンコードを担う共有ユニット。 データアクセス (DATA-L2-002) と
DTC (DTC-L2-001) の応答生成から再利用される。
<<<
RELATIONS:
- TYPE: Parent
  VALUE: DATA-L2-002
- TYPE: Parent
  VALUE: DTC-L2-001

[[/SECTION]]
