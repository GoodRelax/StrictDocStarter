[DOCUMENT]
TITLE: SOVD 故障診断 (DTC) 要求仕様 (Diagnostic Trouble Codes)
UID: DOC-SOVD-DTC
VERSION: 1.0

[GRAMMAR]
IMPORT_FROM_FILE: sovd-grammar.sgra

[TEXT]
STATEMENT: >>>
本書は SOVD の **故障診断 (DTC・フリーズフレーム)** の読出・クリア要求を L1→L3 で
定義する。 内部では ISO 14229 (UDS) の 0x19 系 (ReadDTCInformation) / 0x14
(ClearDiagnosticInformation) を SOVD でラップする。 ステークホルダ要求 (L0)・ユースケースは
`01-stakeholder-requirements.sdoc`、 共有の前付けは `00-overview.sdoc`、 認証・認可は
`03-auth.sdoc` を前提とする。

DTC の **読み出し** は安全機能ではないため原則 **ASIL=QM**。 ただし **「走行中に
安全関連 DTC を消す」 と機能安全評価に影響しうる** ため、 クリアの **走行状態ガードは
ASIL C** とする。 「誰がクリアできるか」 の権限はセキュリティ事項なので **CAL** を付与する。
<<<

[[SECTION]]
TITLE: L1 — システム要求 (System Requirements)

[TEXT]
STATEMENT: >>>
**L1 代表シーケンス: DTC の読み出しと、 走行状態ガード付きクリア**

読み出しは UDS 0x19 へ、 クリアは UDS 0x14 へブリッジする。 クリアは車速ゼロを
確認できた場合のみ実行し、 走行中は 409 で拒否する。

**この図は 15 行を超えるので別文書にしてある** → [LINK: DOC-FIG-DTC-GUARD]
<<<

[REQUIREMENT]
UID: DTC-L1-001
TITLE: DTC リスト取得 API
TYPE: Functional
ASIL: QM
LAYER: L1_System
STATEMENT: >>>
車両は GET /components/{ecu}/faults を提供し、 ステータスマスク
(active/pending/confirmed/permanent) でフィルタ可能とすること。
<<<
RELATIONS:
- TYPE: Parent
  VALUE: DTC-L0-001

[REQUIREMENT]
UID: DTC-L1-002
TITLE: フリーズフレーム取得 API
TYPE: Functional
ASIL: QM
LAYER: L1_System
STATEMENT: >>>
車両は GET /components/{ecu}/faults/{code}/freeze-frame で、 指定 DTC のフリーズフレーム
(発生時の DID 値スナップショット) を JSON で返すこと。
<<<
RELATIONS:
- TYPE: Parent
  VALUE: DTC-L0-002

[REQUIREMENT]
UID: DTC-L1-003
TITLE: DTC クリア API
TYPE: Functional
ASIL: QM
CAL: CAL2
LAYER: L1_System
STATEMENT: >>>
車両は DELETE /components/{ecu}/faults/{code} で DTC をクリアできるようにし、
スコープ write:dtc を要求すること。
<<<
RELATIONS:
- TYPE: Parent
  VALUE: DTC-L0-003

[REQUIREMENT]
UID: DTC-L1-004
TITLE: クリア前の車速ゼロチェック
TYPE: Functional
ASIL: C
LAYER: L1_System
STATEMENT: >>>
DTC クリア要求を受信したとき、 車両は、 現在の車速 (DID 0xF40D) を読み出すこと。 もし車速が 0 km/h でないならば、 車両は、 HTTP 409 Conflict を返すこと。 もし車速を取得できないならば、 車両は、 安全側に倒してクリアを実行せず拒否すること。
<<<
VERIFICATION: >>>
車速 > 0 でのクリア要求が 409 で拒否され、 車速 0 でのみ成功すること。
<<<
RELATIONS:
- TYPE: Parent
  VALUE: DTC-L0-004

[REQUIREMENT]
UID: DTC-L1-005
TITLE: 全 DTC 一括クリア API
TYPE: Functional
ASIL: QM
CAL: CAL2
LAYER: L1_System
STATEMENT: >>>
車両は、 DELETE /components/{ecu}/faults で全 DTC を一括クリアできるように
すること。 このときの車速ゼロの条件は、 DTC-L1-004 と同じであること。
<<<
RELATIONS:
- TYPE: Parent
  VALUE: DTC-L0-003
- TYPE: Parent
  VALUE: DTC-L0-004

[REQUIREMENT]
UID: DTC-L1-006
TITLE: DTC レスポンス時間
TYPE: Non-Functional
ASIL: QM
LAYER: L1_System
STATEMENT: >>>
車両の DTC リスト取得は、 95 パーセンタイルで 1 秒以内に応答すること。
<<<
VERIFICATION: >>>
代表負荷下で、 DTC リスト取得の p95 が 1 秒以内であること。
<<<
RELATIONS:
- TYPE: Parent
  VALUE: DTC-L1-001

[REQUIREMENT]
UID: DTC-L1-007
TITLE: DTC 発生履歴
TYPE: Functional
ASIL: QM
LAYER: L1_System
STATEMENT: >>>
車両は、 直近 1024 件 (概ね 24 時間相当) の DTC 発生履歴を保持し、 GET
/components/{ecu}/faults/history で取得できるようにすること。
<<<
RELATIONS:
- TYPE: Parent
  VALUE: DTC-L0-001

[REQUIREMENT]
UID: DTC-L1-008
TITLE: 安全関連 DTC クリアの権限検証
TYPE: Functional
ASIL: QM
CAL: CAL2
LAYER: L1_System
STATEMENT: >>>
もし安全関連 DTC のクリアが要求されたならば、 車両は、 write:dtc:safety スコープを
検証すること。 もしそのスコープを欠くならば、 車両は、 HTTP 403 を返すこと。
<<<
VERIFICATION: >>>
安全関連 DTC のクリアが、 write:dtc のみのトークンで 403、 write:dtc:safety を
伴う場合に許可されること。
<<<
RELATIONS:
- TYPE: Parent
  VALUE: DTC-L0-006

[[/SECTION]]

[[SECTION]]
TITLE: L2 — ECU ソフトウェア要求 (ECU Software Requirements)

[REQUIREMENT]
UID: DTC-L2-001
TITLE: UDS 0x19 ReadDTCInformation ブリッジ
TYPE: Functional
ASIL: QM
LAYER: L2_ECU_SW
STATEMENT: >>>
SOVD GET /faults 要求を受けたとき、 ゲートウェイ ECU は担当 ECU 群へ UDS Service
0x19 SubFunction 0x02 (reportDTCByStatusMask) を発行し、 結果を集約して JSON で
返すこと。
<<<
RELATIONS:
- TYPE: Parent
  VALUE: DTC-L1-001

[REQUIREMENT]
UID: DTC-L2-002
TITLE: フリーズフレーム取得
TYPE: Functional
ASIL: QM
LAYER: L2_ECU_SW
STATEMENT: >>>
ゲートウェイ ECU は、 UDS 0x19 SubFunction 0x04
(reportDTCSnapshotRecordByDTCNumber) を用いてフリーズフレームを取得すること。
<<<
RELATIONS:
- TYPE: Parent
  VALUE: DTC-L1-002

[REQUIREMENT]
UID: DTC-L2-003
TITLE: UDS 0x14 ClearDiagnosticInformation
TYPE: Functional
ASIL: QM
CAL: CAL2
LAYER: L2_ECU_SW
STATEMENT: >>>
DTC クリア要求に対し、 ゲートウェイ ECU は車速チェック (DTC-L2-004) の成功後に
UDS Service 0x14 を対象 ECU へ発行すること。
<<<
RELATIONS:
- TYPE: Parent
  VALUE: DTC-L1-003

[REQUIREMENT]
UID: DTC-L2-004
TITLE: VehicleSpeedGuard
TYPE: Functional
ASIL: C
LAYER: L2_ECU_SW
STATEMENT: >>>
全ての DTC クリア要求 (個別・一括を問わず) の前に、 ゲートウェイ ECU は VehicleSpeedGuard により車速 == 0 を
100 ms 以内に検証すること。
<<<
VERIFICATION: >>>
車速 > 0 のときクリアが実行されないこと (ガードで阻止) を確認する。
<<<
RELATIONS:
- TYPE: Parent
  VALUE: DTC-L1-004

[REQUIREMENT]
UID: DTC-L2-005
TITLE: DTC マスタテーブル
TYPE: Functional
ASIL: QM
LAYER: L2_ECU_SW
STATEMENT: >>>
ゲートウェイ ECU は、 OEM 提供の DTC マスタテーブル (コード → 説明 / 推奨対処) を
NVRAM に保持し、 API レスポンスに同梱すること。
<<<
RELATIONS:
- TYPE: Parent
  VALUE: DTC-L1-001

[REQUIREMENT]
UID: DTC-L2-006
TITLE: DTC 履歴循環バッファ
TYPE: Functional
ASIL: QM
LAYER: L2_ECU_SW
STATEMENT: >>>
ゲートウェイ ECU は、 タイムスタンプ・DTC・status mask を 1 エントリとする
DTC 履歴を、 最大 1024 件まで循環バッファで保持すること。
<<<
RELATIONS:
- TYPE: Parent
  VALUE: DTC-L1-007

[REQUIREMENT]
UID: DTC-L2-007
TITLE: UDS タイムアウト
TYPE: Non-Functional
ASIL: QM
LAYER: L2_ECU_SW
STATEMENT: >>>
ゲートウェイ ECU の UDS 要求の P2 タイムアウトは 50 ms、 P2* タイムアウトは
500 ms とすること。
<<<
RELATIONS:
- TYPE: Parent
  VALUE: DTC-L1-006

[REQUIREMENT]
UID: DTC-L2-008
TITLE: NRC ハンドリング
TYPE: Constraint
ASIL: QM
LAYER: L2_ECU_SW
STATEMENT: >>>
もし UDS Negative Response Code (NRC) を受けた場合、 ゲートウェイ ECU は SOVD
クライアントへ HTTP 502 と、 JSON ボディに NRC コードを含めて返すこと。
<<<
RELATIONS:
- TYPE: Parent
  VALUE: DTC-L2-001

[[/SECTION]]

[[SECTION]]
TITLE: L3 — ユニット要求 (Unit / Software Component Requirements)

[REQUIREMENT]
UID: DTC-L3-001
TITLE: DtcParser ユニット
TYPE: Functional
ASIL: QM
LAYER: L3_Unit
STATEMENT: >>>
DtcParser ユニットは、 UDS 0x19 のバイナリ応答を解析し、 (dtc_code, status_byte) の
リストを返すこと。
<<<
RELATIONS:
- TYPE: Parent
  VALUE: DTC-L2-001

[REQUIREMENT]
UID: DTC-L3-002
TITLE: FreezeFrameDecoder ユニット
TYPE: Functional
ASIL: QM
LAYER: L3_Unit
STATEMENT: >>>
FreezeFrameDecoder ユニットは、 UDS 0x19/0x04 のフリーズフレームペイロードを
(did, value) のリストに変換すること。
<<<
RELATIONS:
- TYPE: Parent
  VALUE: DTC-L2-002

[REQUIREMENT]
UID: DTC-L3-003
TITLE: SpeedReader ユニット
TYPE: Functional
ASIL: C
LAYER: L3_Unit
STATEMENT: >>>
SpeedReader ユニットは、 ASIL C 認定のリアルタイムタスクとして DID 0xF40D を 10 ms
周期で更新し、 最新値を const アクセスで提供すること。
<<<
RELATIONS:
- TYPE: Parent
  VALUE: DTC-L2-004

[REQUIREMENT]
UID: DTC-L3-004
TITLE: DtcHistoryStore ユニット
TYPE: Functional
ASIL: QM
LAYER: L3_Unit
STATEMENT: >>>
DtcHistoryStore ユニットは、 ロックフリーのリングバッファ (Single Producer Multiple
Consumer) として実装し、 サイズ 1024 を NVRAM 上に確保すること。
<<<
RELATIONS:
- TYPE: Parent
  VALUE: DTC-L2-006

[REQUIREMENT]
UID: DTC-L3-005
TITLE: NVRAM 摩耗保護
TYPE: Constraint
ASIL: QM
LAYER: L3_Unit
STATEMENT: >>>
DTC 履歴の NVRAM 書込は wear-leveling アルゴリズム (例: log-structured) を採用し、
同一セクタへの連続書込を避けること。
<<<
RELATIONS:
- TYPE: Parent
  VALUE: DTC-L3-004

[[/SECTION]]
