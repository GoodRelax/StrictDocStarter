[DOCUMENT]
TITLE: SOVD ソフトウェア更新 (OTA) 要求仕様 (Software Update)
UID: DOC-SOVD-UPDATE
VERSION: 1.0

[GRAMMAR]
IMPORT_FROM_FILE: sovd-grammar.sgra

[TEXT]
STATEMENT: >>>
本書は SOVD 経由の **OTA (Over-The-Air) ソフトウェア更新** の要求を L1 (システム) から
L3 (ユニット) で定義する。 ダウンロード・署名検証・インストール・ロールバックの 4
フェーズと、 機能安全 (ISO 26262) 関連 ECU の更新時保護を含む。 ステークホルダ要求
(L0)・ユースケースは `01-stakeholder-requirements.sdoc` を、 共有の前付けは
`00-overview.sdoc` を、 認証・認可は `03-auth.sdoc` を前提とする。

本書は **安全 (ASIL) とセキュリティ (CAL) が交差する** ドメインである。 走行中の
フラッシュ書込禁止は **安全 (ASIL D)**、 署名検証は **改ざん FW の適用阻止** であり
安全とセキュリティの両面を持つため **ASIL D かつ CAL4** を付与する (00-overview §6.3)。
<<<

[[SECTION]]
TITLE: L1 — システム要求 (System Requirements)

[TEXT]
STATEMENT: >>>
**L1 の状態機械: OTA 更新フェーズ**

OTA 更新は次の状態機械に従う。 署名検証 (Verifying) に失敗したら Installing へ
遷移せず Failed とし、 書込 (Installing) に失敗したら RolledBack で旧バージョンへ戻す。
これにより「未検証パッケージの適用」 を構造的に禁止する (SWU-L1-008)。

.. raw:: html

    <pre class="mermaid">
    stateDiagram-v2
        [*] --> Idle
        Idle --> Downloading: POST /updates
        Downloading --> Verifying: package received
        Verifying --> Installing: signature valid
        Verifying --> Failed: signature invalid
        Installing --> Activated: flash OK
        Installing --> RolledBack: flash error
        Activated --> [*]
        RolledBack --> Idle
        Failed --> Idle
    </pre>
<<<

[REQUIREMENT]
UID: SWU-L1-001
TITLE: 更新パッケージのダウンロード
TYPE: Functional
ASIL: QM
CAL: CAL3
LAYER: L1_System
STATEMENT: >>>
車両は POST /updates エンドポイントを提供し、 OEM サーバから更新パッケージ
(バイナリ + マニフェスト + 署名) を取得すること。
<<<
RELATIONS:
- TYPE: Parent
  VALUE: SWU-L0-001
- TYPE: Parent
  VALUE: SWU-L0-007

[REQUIREMENT]
UID: SWU-L1-002
TITLE: パッケージ署名検証
TYPE: Functional
ASIL: D
CAL: CAL4
LAYER: L1_System
STATEMENT: >>>
パッケージをダウンロードしたとき、 車両は OEM ルート証明書チェーンで RSA-PSS 2048-bit 以上の署名を検証すること。
<<<
VERIFICATION: >>>
改ざんされたパッケージの署名検証が失敗 (invalid) と判定されること。
<<<
RELATIONS:
- TYPE: Parent
  VALUE: SWU-L0-002

[REQUIREMENT]
UID: SWU-L1-003
TITLE: A/B パーティション切替
TYPE: Functional
ASIL: D
LAYER: L1_System
STATEMENT: >>>
車両の ECU は A/B パーティション構成を持ち、 新ファームウェアを非アクティブ
パーティションに書込み、 ブートローダ経由で切替えること。 もし切替えに失敗した場合は
前パーティションを維持すること。
<<<
RELATIONS:
- TYPE: Parent
  VALUE: SWU-L0-003

[REQUIREMENT]
UID: SWU-L1-004
TITLE: 走行状態ガード
TYPE: Functional
ASIL: D
LAYER: L1_System
STATEMENT: >>>
フラッシュ書込を開始する前に、 車両は、 (a) 車速 0、 (b) パーキングブレーキ ON、
(c) シフト P、 (d) IG-OFF または ACC 状態、 の 4 条件をすべて満たすことを
確認すること。
<<<
VERIFICATION: >>>
4 条件のいずれかが崩れている状態で、 フラッシュ書込が開始されないこと。
<<<
RELATIONS:
- TYPE: Parent
  VALUE: SWU-L0-004

[REQUIREMENT]
UID: SWU-L1-005
TITLE: ロールバック API
TYPE: Functional
ASIL: C
LAYER: L1_System
STATEMENT: >>>
車両は POST /updates/rollback で前バージョンへの即時ロールバックを実行できるように
すること。 ロールバック実行中は、 本システムは新規の更新・フラッシュ書込・診断書込系の操作要求を受け付けないこと。
<<<
RELATIONS:
- TYPE: Parent
  VALUE: SWU-L0-003

[REQUIREMENT]
UID: SWU-L1-006
TITLE: 更新進捗ストリーム
TYPE: Functional
ASIL: QM
LAYER: L1_System
STATEMENT: >>>
車両は GET /updates/progress (Server-Sent Events) で、 各 ECU の更新進捗 (0..100%) と
現フェーズを SOVD クライアントへプッシュ通知すること。
<<<
RELATIONS:
- TYPE: Parent
  VALUE: SWU-L0-008

[REQUIREMENT]
UID: SWU-L1-007
TITLE: 中断耐性
TYPE: Functional
ASIL: QM
LAYER: L1_System
STATEMENT: >>>
もし更新中に電源断・通信切断が発生した場合、 再開時に車両は、 ダウンロード中であれば
再開、 書込中であれば最初からリトライ、 完了済であればスキップとすること。
<<<
RELATIONS:
- TYPE: Parent
  VALUE: SWU-L0-003

[REQUIREMENT]
UID: SWU-L1-008
TITLE: OTA 状態機械の遵守
TYPE: Functional
ASIL: D
CAL: CAL4
LAYER: L1_System
STATEMENT: >>>
車両の OTA 更新は、 上図の状態機械に従うこと。 もし署名検証 (Verifying) に
失敗したならば、 車両は、 Installing に遷移せず Failed とすること。 もしフラッシュに
失敗したならば、 車両は、 RolledBack で旧版に戻すこと。
<<<
RATIONALE: >>>
署名検証に失敗したパッケージの適用を、 状態遷移によって構造的に禁止する。 同じ状態機械がフラッシュ失敗時の RolledBack 遷移も扱うため、 改ざん検知 (SWU-L0-002) と書込失敗時の自動ロールバックを 1 状態機械で満たす収束 (N→1) の例 (異常検出・手動ロールバックは SWU-L1-005 が担う)。
<<<
RELATIONS:
- TYPE: Parent
  VALUE: SWU-L0-006
- TYPE: Parent
  VALUE: SWU-L0-003

[[/SECTION]]

[[SECTION]]
TITLE: L2 — ECU ソフトウェア要求 (ECU Software Requirements)

[REQUIREMENT]
UID: SWU-L2-001
TITLE: ダウンロードマネージャ
TYPE: Functional
ASIL: QM
CAL: CAL3
LAYER: L2_ECU_SW
STATEMENT: >>>
ゲートウェイ ECU は DownloadManager を実装し、 HTTPS Range リクエストによる分割
ダウンロード・進捗報告・整合性チェック (SHA-256) を行うこと。
<<<
RELATIONS:
- TYPE: Parent
  VALUE: SWU-L1-001

[REQUIREMENT]
UID: SWU-L2-002
TITLE: 署名検証エンジン
TYPE: Functional
ASIL: D
CAL: CAL4
LAYER: L2_ECU_SW
STATEMENT: >>>
SignatureVerifier は ECDSA P-256 と RSA-PSS 2048 の両方をサポートし、 OEM ルート CA で
署名チェーンを検証すること。
<<<
RELATIONS:
- TYPE: Parent
  VALUE: SWU-L1-002

[REQUIREMENT]
UID: SWU-L2-003
TITLE: フラッシュ書込ドライバ
TYPE: Functional
ASIL: D
LAYER: L2_ECU_SW
STATEMENT: >>>
FlashWriter は ECU 内 NOR フラッシュへの書込を担い、 書込後に CRC32 ベリファイを
必須とすること。
<<<
RELATIONS:
- TYPE: Parent
  VALUE: SWU-L1-003

[REQUIREMENT]
UID: SWU-L2-004
TITLE: VehicleStateGuard
TYPE: Functional
ASIL: D
LAYER: L2_ECU_SW
STATEMENT: >>>
更新を開始する前から、 VehicleStateGuard は、 SWU-L1-004 の 4 条件を 50 ms 周期で
監視すること。 もし 1 つでも崩れたならば、 VehicleStateGuard は、 書込を緊急中断
すること。
<<<
RELATIONS:
- TYPE: Parent
  VALUE: SWU-L1-004

[REQUIREMENT]
UID: SWU-L2-005
TITLE: ロールバックマネージャ
TYPE: Functional
ASIL: C
LAYER: L2_ECU_SW
STATEMENT: >>>
RollbackManager は、 前バージョンのパーティション情報を保持すること。
ロールバックを要求されたとき、 RollbackManager は、 ブートローダパラメータを
書き換えて再起動を要求すること。
<<<
RELATIONS:
- TYPE: Parent
  VALUE: SWU-L1-005

[REQUIREMENT]
UID: SWU-L2-006
TITLE: 進捗イベントバス
TYPE: Functional
ASIL: QM
LAYER: L2_ECU_SW
STATEMENT: >>>
各更新フェーズ (download / verify / write / finalize) は ProgressEventBus にイベントを
publish し、 SSE エンドポイントが subscribe して配信すること。
<<<
RELATIONS:
- TYPE: Parent
  VALUE: SWU-L1-006

[REQUIREMENT]
UID: SWU-L2-007
TITLE: 再開可能ステートマシン
TYPE: Functional
ASIL: QM
LAYER: L2_ECU_SW
STATEMENT: >>>
更新ステートマシンの状態は不揮発領域に保存され、 電源断後の再起動で最後の安全状態から
再開できること。
<<<
RELATIONS:
- TYPE: Parent
  VALUE: SWU-L1-007

[REQUIREMENT]
UID: SWU-L2-008
TITLE: ASIL D 開発プロセス
TYPE: Constraint
ASIL: D
LAYER: L2_ECU_SW
STATEMENT: >>>
SignatureVerifier / FlashWriter / VehicleStateGuard は ISO 26262 ASIL D 準拠の開発
プロセスで構築し、 ユニットテストカバレッジ 100% を達成すること。
<<<
RELATIONS:
- TYPE: Parent
  VALUE: SWU-L1-002

[[/SECTION]]

[[SECTION]]
TITLE: L3 — ユニット要求 (Unit / Software Component Requirements)

[REQUIREMENT]
UID: SWU-L3-001
TITLE: PackageDownloader ユニット
TYPE: Functional
ASIL: QM
CAL: CAL3
LAYER: L3_Unit
STATEMENT: >>>
PackageDownloader ユニットは、 1 MB チャンク単位の HTTPS Range ダウンロードを実装し、
失敗時のリトライ (指数バックオフ 1s..30s) を提供すること。
<<<
RELATIONS:
- TYPE: Parent
  VALUE: SWU-L2-001

[REQUIREMENT]
UID: SWU-L3-002
TITLE: SignatureVerifier ユニット
TYPE: Functional
ASIL: D
CAL: CAL4
LAYER: L3_Unit
STATEMENT: >>>
SignatureVerifier ユニットは、 OpenSSL を用いて ECDSA P-256 および RSA-PSS 2048 の
署名を検証する、 内部状態を持たない純粋関数として実装すること。
<<<
RELATIONS:
- TYPE: Parent
  VALUE: SWU-L2-002

[REQUIREMENT]
UID: SWU-L3-003
TITLE: FlashSectorWriter ユニット
TYPE: Functional
ASIL: D
LAYER: L3_Unit
STATEMENT: >>>
FlashSectorWriter ユニットは、 64 KB セクタの消去・書込・CRC32 計算を提供すること。
write 操作は、 事前のセクタ消去を必須とすること。 もし消去または書込に失敗したならば、
FlashSectorWriter ユニットは、 ERROR_FLASH_VERIFY を返すこと。
<<<
RELATIONS:
- TYPE: Parent
  VALUE: SWU-L2-003

[REQUIREMENT]
UID: SWU-L3-004
TITLE: VehicleStateMonitor ユニット
TYPE: Functional
ASIL: D
LAYER: L3_Unit
STATEMENT: >>>
VehicleStateMonitor ユニットは、 車速・パーキングブレーキ・シフト・IG 信号を CAN
から読み出すこと。 もし全条件を満たすならば、 VehicleStateMonitor ユニットは、
TRUE を返すこと。 満たさないならば、 FALSE を返すこと。
<<<
RELATIONS:
- TYPE: Parent
  VALUE: SWU-L2-004

[REQUIREMENT]
UID: SWU-L3-005
TITLE: 開発言語制限
TYPE: Constraint
ASIL: D
LAYER: L3_Unit
STATEMENT: >>>
ASIL D 認定ユニットは、 MISRA C:2012 準拠の C 言語のみで実装し、 動的メモリ確保禁止・
再帰呼出禁止・全関数の循環的複雑度 <= 10 とすること。
<<<
RELATIONS:
- TYPE: Parent
  VALUE: SWU-L2-008

[[/SECTION]]
