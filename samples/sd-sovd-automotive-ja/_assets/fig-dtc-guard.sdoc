[DOCUMENT]
TITLE: 図 - DTC 消去のガード条件
UID: DOC-FIG-DTC-GUARD

[TEXT]
STATEMENT: >>>
.. raw:: html

    <pre class="mermaid">
    sequenceDiagram
        participant C as SOVD Client
        participant G as Gateway ECU
        participant E as ECU
        C->>G: GET /components/engine/faults (Bearer JWT)
        G->>E: UDS 0x19 02 (reportDTCByStatusMask)
        E-->>G: DTC list + status
        G-->>C: 200 OK [{code, status}]
        C->>G: DELETE /components/engine/faults (scope write:dtc)
        G->>G: read vehicle speed (DID 0xF40D)
        alt vehicle stopped (speed == 0)
            G->>E: UDS 0x14 (ClearDiagnosticInformation)
            G-->>C: 204 No Content
        else vehicle moving (speed > 0)
            G-->>C: 409 Conflict
        end
    </pre>
<<<
