[DOCUMENT]
TITLE: 図 - 中核のクラス構成
UID: DOC-FIG-ARCH-CLASS-CORE

[TEXT]
STATEMENT: >>>
.. raw:: html

    <pre class="mermaid">
    classDiagram
        class DataReadUseCase {
            +read(ecu, did) Json
        }
        class ScopeAuthorizer {
            +authorize(required, scopes) Decision
        }
        class TokenVerifier {
            +verify(jwt) VerifyResult
        }
        class DidResolver {
            +resolve(did) EcuAddress
        }
        class UdsClient {
            +readDataByIdentifier(addr, did) Bytes
        }
        class JsonSerializer {
            +serialize(value) Json
        }
        DataReadUseCase --> ScopeAuthorizer : uses
        DataReadUseCase --> DidResolver : uses
        DataReadUseCase --> UdsClient : uses
        DataReadUseCase --> JsonSerializer : uses
        ScopeAuthorizer ..> TokenVerifier : reads claims
    </pre>
<<<
